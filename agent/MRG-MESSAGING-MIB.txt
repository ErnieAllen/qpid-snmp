MRG-MESSAGING-MIB DEFINITIONS ::= BEGIN

--
-- Apache amqp messaging MIB for Red Hat MRG qpid broker
--
-- This file is generated from management-schema.xml found in the apache qpid packages
-- using qpid-snmp-mibgen and qpid-snmp.txt.
-- Do not edit this mib file directly, instead generate it using
-- qpid-snmp-mibgen \
--	-s $QPID/specs/management-schema.xml \
--  -s $QPID/cpp/src/qpid/acl/management-schema.xml \
--  -s $QPID/cpp/src/qpid/cluster/management-schema.xml \
--  -s $QPID/cpp/src/qpid/ha/management-schema.xml \
--  -m MRG-MESSAGING-MIB.txt 
-- 
--
-- iso(1).org(3).dod(6).internet(1).private(4).enterprises(1)
--                             |
--                       apache(18060)
--                             |
--                    _________________________
--                   |                         |
--               amqp(5672)            other apache OIDs (https://cwiki.apache.org/DIRxPMGT/oid-assignment-scheme.html)
--                   |
--           ___________________
--          |                   |
--      amqp010(1)       amqp10(2) - reserved for future use
--          |
--           ___________________________________________________________________
--          |                                                                   |
--
--      qpid010(1) this mib defines this node and all its child nodes         [other amqp101 based products]...
--          |
--        ____________________________________________________________________________________________________________________
--       |                                                                    |                           |                   |
--	  qpid010BrokerClasses(1)                                      qpid010Plugins(2)              qpid010Performance(3)    qpid010Events(4)
--       |                                                                    |                           |
--  <qpid010System, qpid010Memory, qpid010Broker...>    [qpid010Acl, qpid010Cluster, qpid010HA]        qpidCnfGroups(1)
--                                                                                                        |
--                                                                         _______________________________________________
--                                                                        |           |                                   |
--                                                          qpidCnfGrpRequired(1) qpidCnfGrpOptional(2)   qpidCnfGrpArguments(3)    ...

IMPORTS
        MODULE-IDENTITY, OBJECT-IDENTITY, OBJECT-TYPE, Counter64,
                Counter32, Integer32, Unsigned32, TimeTicks, enterprises,
                NOTIFICATION-TYPE
            FROM SNMPv2-SMI
        OBJECT-GROUP, NOTIFICATION-GROUP, MODULE-COMPLIANCE
            FROM SNMPv2-CONF
        TruthValue, TEXTUAL-CONVENTION
            FROM SNMPv2-TC;

apacheAMQP MODULE-IDENTITY
        LAST-UPDATED "201207130000Z"
        ORGANIZATION "www.redhat.com"
        CONTACT-INFO
                "e-mail: eallen@redhat.com"
        DESCRIPTION
            "Root for apache amqp qpid messaging nodes"
        REVISION "201207130000Z"
            DESCRIPTION
                "First release"
        ::= { enterprises 18060 }
--
-- TEXTUAL-CONVENTIONS to define the qpid data types that don't
-- map directly to mib types
-- Note: mib types must begin with a cap, qpid types are normally
-- all lower case
-- __________________________________________________________________
Uuid ::= TEXTUAL-CONVENTION
        DISPLAY-HINT    "8a-4a-4a-4a-12a"
        STATUS          current
        DESCRIPTION     "The system generates uuids that look like dd29e3bc-6acd-4f9e-8672-5c9c0bf716a7"
        SYNTAX          OCTET STRING (SIZE (36))

Sstr ::= TEXTUAL-CONVENTION
        DISPLAY-HINT    "255a"
        STATUS          current
        DESCRIPTION     "Short string 0 - 255 characters"
        SYNTAX          OCTET STRING (SIZE (0..255))

Lstr ::= TEXTUAL-CONVENTION
        DISPLAY-HINT    "65535a"
        STATUS          current
        DESCRIPTION     "Long string"
        SYNTAX          OCTET STRING (SIZE (0..65535))

ObjId ::= TEXTUAL-CONVENTION
        DISPLAY-HINT    "255a"
        STATUS          current
        DESCRIPTION     "Internal field that references another qpid object."
        SYNTAX          OCTET STRING (SIZE (0..255))

Uint64 ::= TEXTUAL-CONVENTION
        DISPLAY-HINT    "d"
        STATUS          current
        DESCRIPTION     "There is no mib 64 unsigned, so use Counter64"
        SYNTAX          Counter64

Uint16 ::= TEXTUAL-CONVENTION
        DISPLAY-HINT    "d"
        STATUS          current
        DESCRIPTION     "There is no mib 16 unsigned, so use Integer"
        SYNTAX          Integer32

Hilo32 ::= TEXTUAL-CONVENTION
        DISPLAY-HINT    "d"
        STATUS          current
        DESCRIPTION     "Each Hilo32 data object is one of three data values:
                        1. The current data value at the time of the get request.
                        2. The highest value for the reporting interval
                        3. The lowest value for the reporting interval"
        SYNTAX          Integer32

Map ::= TEXTUAL-CONVENTION
        DISPLAY-HINT    "65535a"
        STATUS          current
        DESCRIPTION     "Textual representation of a map<string, string>"
        SYNTAX          OCTET STRING (SIZE (0..65535))

--
-- This object and the qpqcheAMQP object should probably be stored in a separate MIB
-- and imported
--
amqp010 OBJECT-IDENTITY
        STATUS      current
        DESCRIPTION
        "Version 010 amqp"
        ::= { apacheAMQP 5672 }

--
-- The root OID for this MIB
-- _____________________________________________________________________
qpid010 OBJECT-IDENTITY
        STATUS      current
        DESCRIPTION
        "RedHat qpid implementation"
        ::= { amqp010 1 }

qpid010BrokerClasses OBJECT-IDENTITY
        STATUS      current
        DESCRIPTION
        "Root for all broker classes defined in $QPIDROOT/specs/management-schema.xml"
        ::= { qpid010 1 }
--
--
-- Parent node for amqp 0.10 messaging broker plugins
--
qpid010Plugins OBJECT-IDENTITY
        STATUS      current
        DESCRIPTION
        "Parent node for all amqp 0.10 broker plugins"
        ::= { qpid010 2 }

--
-- Parent node for amqp 0.10 conformance groupings
--
qpid010Conformance OBJECT-IDENTITY
        STATUS      current
        DESCRIPTION "The parent for all conformance objects"
        ::= { qpid010 3 }

--
-- Parent node for events
--
qpid010Events OBJECT-IDENTITY
        STATUS      current
        DESCRIPTION "The parent for all qpid events"
        ::= { qpid010 4 }

--
-- Define the OID for each top level messaging class
-- ______________________________________________________________

qpid010System OBJECT-IDENTITY
        STATUS      current
        DESCRIPTION "The parent of the System properties"
        ::= { qpid010BrokerClasses 1 }

qpid010Memory OBJECT-IDENTITY
        STATUS      current
        DESCRIPTION "The parent of the Memory properties"
        ::= { qpid010BrokerClasses 2 }

qpid010Broker OBJECT-IDENTITY
        STATUS      current
        DESCRIPTION "The parent of the Broker properties"
        ::= { qpid010BrokerClasses 3 }

qpid010Agent OBJECT-IDENTITY
        STATUS      current
        DESCRIPTION "The parent of the Agent properties"
        ::= { qpid010BrokerClasses 4 }

qpid010Vhosts OBJECT-IDENTITY
        STATUS      current
        DESCRIPTION "Table for all the Vhosts"
        ::= { qpid010BrokerClasses 5 }

qpid010Queues OBJECT-IDENTITY
        STATUS      current
        DESCRIPTION "Table for all the Queues"
        ::= { qpid010BrokerClasses 6 }

qpid010Exchanges OBJECT-IDENTITY
        STATUS      current
        DESCRIPTION "Table for all the Exchanges"
        ::= { qpid010BrokerClasses 7 }

qpid010Bindings OBJECT-IDENTITY
        STATUS      current
        DESCRIPTION "Table for all the Bindings"
        ::= { qpid010BrokerClasses 8 }

qpid010Subscriptions OBJECT-IDENTITY
        STATUS      current
        DESCRIPTION "Table for all the Subscriptions"
        ::= { qpid010BrokerClasses 9 }

qpid010Connections OBJECT-IDENTITY
        STATUS      current
        DESCRIPTION "Table for all the Connections"
        ::= { qpid010BrokerClasses 10 }

qpid010Links OBJECT-IDENTITY
        STATUS      current
        DESCRIPTION "Table for all the Links"
        ::= { qpid010BrokerClasses 11 }

qpid010Bridges OBJECT-IDENTITY
        STATUS      current
        DESCRIPTION "Table for all the Bridges"
        ::= { qpid010BrokerClasses 12 }

qpid010Sessions OBJECT-IDENTITY
        STATUS      current
        DESCRIPTION "Table for all the Sessions"
        ::= { qpid010BrokerClasses 13 }

qpid010ManagementSetupState OBJECT-IDENTITY
        STATUS      current
        DESCRIPTION "The parent of the ManagementSetupState properties"
        ::= { qpid010BrokerClasses 14 }

qpid010Acl OBJECT-IDENTITY
        STATUS      current
        DESCRIPTION "The parent of the plugin Acl properties"
        ::= { qpid010Plugins 1 }

qpid010Cluster OBJECT-IDENTITY
        STATUS      current
        DESCRIPTION "The parent of the plugin Cluster properties"
        ::= { qpid010Plugins 2 }

qpid010HaBroker OBJECT-IDENTITY
        STATUS      current
        DESCRIPTION "The parent of the plugin HaBroker properties"
        ::= { qpid010Plugins 3 }


--
-- Define the [table]/data for each of the top level classes
-- ______________________________________________________________
-- ______________________________________________________________
-- System class properties and statistics
-- ______________________________________________________________

--
-- The SystemSystemId data object
--
qpid010SystemSystemId OBJECT-TYPE
        SYNTAX      Uuid
        MAX-ACCESS  read-write
        STATUS      current
        DESCRIPTION "System systemId
                     Additional info ( nodeType:property, index:y )"
        ::= { qpid010System 1 }

--
-- The SystemOsName data object
--
qpid010SystemOsName OBJECT-TYPE
        SYNTAX      Sstr
        MAX-ACCESS  read-only
        STATUS      current
        DESCRIPTION "Operating System Name
                     Additional info ( nodeType:property )"
        ::= { qpid010System 2 }

--
-- The SystemNodeName data object
--
qpid010SystemNodeName OBJECT-TYPE
        SYNTAX      Sstr
        MAX-ACCESS  read-only
        STATUS      current
        DESCRIPTION "Node Name
                     Additional info ( nodeType:property )"
        ::= { qpid010System 3 }

--
-- The SystemRelease data object
--
qpid010SystemRelease OBJECT-TYPE
        SYNTAX      Sstr
        MAX-ACCESS  read-only
        STATUS      current
        DESCRIPTION "System release
                     Additional info ( nodeType:property )"
        ::= { qpid010System 4 }

--
-- The SystemVersion data object
--
qpid010SystemVersion OBJECT-TYPE
        SYNTAX      Sstr
        MAX-ACCESS  read-only
        STATUS      current
        DESCRIPTION "System version
                     Additional info ( nodeType:property )"
        ::= { qpid010System 5 }

--
-- The SystemMachine data object
--
qpid010SystemMachine OBJECT-TYPE
        SYNTAX      Sstr
        MAX-ACCESS  read-only
        STATUS      current
        DESCRIPTION "System machine
                     Additional info ( nodeType:property )"
        ::= { qpid010System 6 }

-- ______________________________________________________________
-- Memory class properties and statistics
-- ______________________________________________________________

--
-- The MemoryName data object
--
qpid010MemoryName OBJECT-TYPE
        SYNTAX      Sstr
        MAX-ACCESS  read-write
        STATUS      current
        DESCRIPTION "Index for the broker at this agent
                     Additional info ( nodeType:property, index:y )"
        ::= { qpid010Memory 1 }

--
-- The MemoryMallocarena data object
--
qpid010MemoryMallocarena OBJECT-TYPE
        SYNTAX      Uint64
        MAX-ACCESS  read-only
        STATUS      current
        DESCRIPTION "Total size of memory allocated with `sbrk' by `malloc', in bytes
                     Additional info ( nodeType:property, optional:y )"
        ::= { qpid010Memory 2 }

--
-- The MemoryMallocordblks data object
--
qpid010MemoryMallocordblks OBJECT-TYPE
        SYNTAX      Uint64
        MAX-ACCESS  read-only
        STATUS      current
        DESCRIPTION "The number of chunks not in use
                     Additional info ( nodeType:property, optional:y )"
        ::= { qpid010Memory 3 }

--
-- The MemoryMallochblks data object
--
qpid010MemoryMallochblks OBJECT-TYPE
        SYNTAX      Uint64
        MAX-ACCESS  read-only
        STATUS      current
        DESCRIPTION "Total number of chunks allocated with `mmap'
                     Additional info ( nodeType:property, optional:y )"
        ::= { qpid010Memory 4 }

--
-- The MemoryMallochblkhd data object
--
qpid010MemoryMallochblkhd OBJECT-TYPE
        SYNTAX      Uint64
        MAX-ACCESS  read-only
        STATUS      current
        DESCRIPTION "Total size of memory allocated with `mmap', in bytes
                     Additional info ( nodeType:property, optional:y )"
        ::= { qpid010Memory 5 }

--
-- The MemoryMallocuordblks data object
--
qpid010MemoryMallocuordblks OBJECT-TYPE
        SYNTAX      Uint64
        MAX-ACCESS  read-only
        STATUS      current
        DESCRIPTION "Total size of memory occupied by chunks handed out by `malloc'
                     Additional info ( nodeType:property, optional:y )"
        ::= { qpid010Memory 6 }

--
-- The MemoryMallocfordblks data object
--
qpid010MemoryMallocfordblks OBJECT-TYPE
        SYNTAX      Uint64
        MAX-ACCESS  read-only
        STATUS      current
        DESCRIPTION "Total size of memory occupied by free (not in use) chunks
                     Additional info ( nodeType:property, optional:y )"
        ::= { qpid010Memory 7 }

--
-- The MemoryMallockeepcost data object
--
qpid010MemoryMallockeepcost OBJECT-TYPE
        SYNTAX      Uint64
        MAX-ACCESS  read-only
        STATUS      current
        DESCRIPTION "The size of the top-most releasable chunk that normally borders the end of the heap
                     Additional info ( nodeType:property, optional:y )"
        ::= { qpid010Memory 8 }

-- ______________________________________________________________
-- Broker class properties and statistics
-- ______________________________________________________________

--
-- The BrokerName data object
--
qpid010BrokerName OBJECT-TYPE
        SYNTAX      Sstr
        MAX-ACCESS  read-write
        STATUS      current
        DESCRIPTION "Index for the broker at this agent
                     Additional info ( nodeType:property, index:y )"
        ::= { qpid010Broker 1 }

--
-- The BrokerSystemRef data object
--
qpid010BrokerSystemRef OBJECT-TYPE
        SYNTAX      ObjId
        MAX-ACCESS  read-only
        STATUS      current
        DESCRIPTION "System ID
                     Additional info ( nodeType:property, references:System, parentRef:y )"
        ::= { qpid010Broker 2 }

--
-- The BrokerPort data object
--
qpid010BrokerPort OBJECT-TYPE
        SYNTAX      Uint16
        MAX-ACCESS  read-only
        STATUS      current
        DESCRIPTION "TCP Port for AMQP Service
                     Additional info ( nodeType:property )"
        ::= { qpid010Broker 3 }

--
-- The BrokerWorkerThreads data object
--
qpid010BrokerWorkerThreads OBJECT-TYPE
        SYNTAX      Uint16
        MAX-ACCESS  read-only
        STATUS      current
        DESCRIPTION "Thread pool size
                     Additional info ( nodeType:property )"
        ::= { qpid010Broker 4 }

--
-- The BrokerConnBacklog data object
--
qpid010BrokerConnBacklog OBJECT-TYPE
        SYNTAX      Uint16
        MAX-ACCESS  read-only
        STATUS      current
        DESCRIPTION "Connection backlog limit for listening socket
                     Additional info ( nodeType:property )"
        ::= { qpid010Broker 5 }

--
-- The BrokerStagingThreshold data object
--
qpid010BrokerStagingThreshold OBJECT-TYPE
        SYNTAX      Unsigned32
        MAX-ACCESS  read-only
        STATUS      current
        DESCRIPTION "Broker stages messages over this size to disk
                     Additional info ( nodeType:property )"
        ::= { qpid010Broker 6 }

--
-- The BrokerMgmtPublish data object
--
qpid010BrokerMgmtPublish OBJECT-TYPE
        SYNTAX      TruthValue
        MAX-ACCESS  read-only
        STATUS      current
        DESCRIPTION "Broker's management agent sends unsolicited data on the publish interval
                     Additional info ( nodeType:property )"
        ::= { qpid010Broker 7 }

--
-- The BrokerMgmtPubInterval data object
--
qpid010BrokerMgmtPubInterval OBJECT-TYPE
        SYNTAX      Uint16
        UNITS       "second"
        MAX-ACCESS  read-write
        STATUS      current
        DESCRIPTION "Interval for management broadcasts
                     Additional info ( nodeType:property, min:1 )"
        ::= { qpid010Broker 8 }

--
-- The BrokerVersion data object
--
qpid010BrokerVersion OBJECT-TYPE
        SYNTAX      Sstr
        MAX-ACCESS  read-only
        STATUS      current
        DESCRIPTION "Running software version
                     Additional info ( nodeType:property )"
        ::= { qpid010Broker 9 }

--
-- The BrokerDataDir data object
--
qpid010BrokerDataDir OBJECT-TYPE
        SYNTAX      Lstr
        MAX-ACCESS  read-only
        STATUS      current
        DESCRIPTION "Persistent configuration storage location
                     Additional info ( nodeType:property, optional:y )"
        ::= { qpid010Broker 10 }

--
-- The BrokerUptime data object
--
qpid010BrokerUptime OBJECT-TYPE
        SYNTAX      TimeTicks
        MAX-ACCESS  read-only
        STATUS      current
        DESCRIPTION "Broker uptime
                     Additional info ( nodeType:statistic )"
        ::= { qpid010Broker 11 }

--
-- The BrokerQueueCount data object
--
qpid010BrokerQueueCount OBJECT-TYPE
        SYNTAX      Counter64
        UNITS       "queue"
        MAX-ACCESS  read-only
        STATUS      current
        DESCRIPTION "Number of queues in the broker
                     Additional info ( nodeType:statistic )"
        ::= { qpid010Broker 12 }

--
-- The BrokerMsgTotalEnqueues data object
--
qpid010BrokerMsgTotalEnqueues OBJECT-TYPE
        SYNTAX      Counter64
        UNITS       "message"
        MAX-ACCESS  read-only
        STATUS      current
        DESCRIPTION "Total messages enqueued to broker
                     Additional info ( nodeType:statistic )"
        ::= { qpid010Broker 13 }

--
-- The BrokerMsgTotalDequeues data object
--
qpid010BrokerMsgTotalDequeues OBJECT-TYPE
        SYNTAX      Counter64
        UNITS       "message"
        MAX-ACCESS  read-only
        STATUS      current
        DESCRIPTION "Total messages dequeued from broker
                     Additional info ( nodeType:statistic )"
        ::= { qpid010Broker 14 }

--
-- The BrokerByteTotalEnqueues data object
--
qpid010BrokerByteTotalEnqueues OBJECT-TYPE
        SYNTAX      Counter64
        UNITS       "octet"
        MAX-ACCESS  read-only
        STATUS      current
        DESCRIPTION "Total bytes enqueued to broker
                     Additional info ( nodeType:statistic )"
        ::= { qpid010Broker 15 }

--
-- The BrokerByteTotalDequeues data object
--
qpid010BrokerByteTotalDequeues OBJECT-TYPE
        SYNTAX      Counter64
        UNITS       "octet"
        MAX-ACCESS  read-only
        STATUS      current
        DESCRIPTION "Total bytes dequeued from broker
                     Additional info ( nodeType:statistic )"
        ::= { qpid010Broker 16 }

--
-- The BrokerMsgDepth data object
--
qpid010BrokerMsgDepth OBJECT-TYPE
        SYNTAX      Counter64
        UNITS       "message"
        MAX-ACCESS  read-only
        STATUS      current
        DESCRIPTION "Current number of messages on queues in broker
                     Additional info ( nodeType:statistic, assign:msgTotalEnqueues - msgTotalDequeues )"
        ::= { qpid010Broker 17 }

--
-- The BrokerByteDepth data object
--
qpid010BrokerByteDepth OBJECT-TYPE
        SYNTAX      Counter64
        UNITS       "octet"
        MAX-ACCESS  read-only
        STATUS      current
        DESCRIPTION "Current number of bytes on queues in broker
                     Additional info ( nodeType:statistic, assign:byteTotalEnqueues - byteTotalDequeues )"
        ::= { qpid010Broker 18 }

--
-- The BrokerMsgPersistEnqueues data object
--
qpid010BrokerMsgPersistEnqueues OBJECT-TYPE
        SYNTAX      Counter64
        UNITS       "message"
        MAX-ACCESS  read-only
        STATUS      current
        DESCRIPTION "Total persistent messages enqueued to broker
                     Additional info ( nodeType:statistic )"
        ::= { qpid010Broker 19 }

--
-- The BrokerMsgPersistDequeues data object
--
qpid010BrokerMsgPersistDequeues OBJECT-TYPE
        SYNTAX      Counter64
        UNITS       "message"
        MAX-ACCESS  read-only
        STATUS      current
        DESCRIPTION "Total persistent messages dequeued from broker
                     Additional info ( nodeType:statistic )"
        ::= { qpid010Broker 20 }

--
-- The BrokerBytePersistEnqueues data object
--
qpid010BrokerBytePersistEnqueues OBJECT-TYPE
        SYNTAX      Counter64
        UNITS       "octet"
        MAX-ACCESS  read-only
        STATUS      current
        DESCRIPTION "Total persistent bytes enqueued to broker
                     Additional info ( nodeType:statistic )"
        ::= { qpid010Broker 21 }

--
-- The BrokerBytePersistDequeues data object
--
qpid010BrokerBytePersistDequeues OBJECT-TYPE
        SYNTAX      Counter64
        UNITS       "octet"
        MAX-ACCESS  read-only
        STATUS      current
        DESCRIPTION "Total persistent bytes dequeued from broker
                     Additional info ( nodeType:statistic )"
        ::= { qpid010Broker 22 }

--
-- The BrokerMsgTxnEnqueues data object
--
qpid010BrokerMsgTxnEnqueues OBJECT-TYPE
        SYNTAX      Counter64
        UNITS       "message"
        MAX-ACCESS  read-only
        STATUS      current
        DESCRIPTION "Total transactional messages enqueued to broker
                     Additional info ( nodeType:statistic )"
        ::= { qpid010Broker 23 }

--
-- The BrokerMsgTxnDequeues data object
--
qpid010BrokerMsgTxnDequeues OBJECT-TYPE
        SYNTAX      Counter64
        UNITS       "message"
        MAX-ACCESS  read-only
        STATUS      current
        DESCRIPTION "Total transactional messages dequeued from broker
                     Additional info ( nodeType:statistic )"
        ::= { qpid010Broker 24 }

--
-- The BrokerByteTxnEnqueues data object
--
qpid010BrokerByteTxnEnqueues OBJECT-TYPE
        SYNTAX      Counter64
        UNITS       "octet"
        MAX-ACCESS  read-only
        STATUS      current
        DESCRIPTION "Total transactional bytes enqueued to broker
                     Additional info ( nodeType:statistic )"
        ::= { qpid010Broker 25 }

--
-- The BrokerByteTxnDequeues data object
--
qpid010BrokerByteTxnDequeues OBJECT-TYPE
        SYNTAX      Counter64
        UNITS       "octet"
        MAX-ACCESS  read-only
        STATUS      current
        DESCRIPTION "Total transactional bytes dequeued from broker
                     Additional info ( nodeType:statistic )"
        ::= { qpid010Broker 26 }

--
-- The BrokerMsgFtdEnqueues data object
--
qpid010BrokerMsgFtdEnqueues OBJECT-TYPE
        SYNTAX      Counter64
        UNITS       "message"
        MAX-ACCESS  read-only
        STATUS      current
        DESCRIPTION "Total message bodies released from memory and flowed-to-disk on broker
                     Additional info ( nodeType:statistic )"
        ::= { qpid010Broker 27 }

--
-- The BrokerMsgFtdDequeues data object
--
qpid010BrokerMsgFtdDequeues OBJECT-TYPE
        SYNTAX      Counter64
        UNITS       "message"
        MAX-ACCESS  read-only
        STATUS      current
        DESCRIPTION "Total message bodies dequeued from the broker having been flowed-to-disk
                     Additional info ( nodeType:statistic )"
        ::= { qpid010Broker 28 }

--
-- The BrokerByteFtdEnqueues data object
--
qpid010BrokerByteFtdEnqueues OBJECT-TYPE
        SYNTAX      Counter64
        UNITS       "octet"
        MAX-ACCESS  read-only
        STATUS      current
        DESCRIPTION "Total bytes released from memory and flowed-to-disk on broker
                     Additional info ( nodeType:statistic )"
        ::= { qpid010Broker 29 }

--
-- The BrokerByteFtdDequeues data object
--
qpid010BrokerByteFtdDequeues OBJECT-TYPE
        SYNTAX      Counter64
        UNITS       "octet"
        MAX-ACCESS  read-only
        STATUS      current
        DESCRIPTION "Total bytes dequeued from the broker having been flowed-to-disk
                     Additional info ( nodeType:statistic )"
        ::= { qpid010Broker 30 }

--
-- The BrokerMsgFtdDepth data object
--
qpid010BrokerMsgFtdDepth OBJECT-TYPE
        SYNTAX      Counter64
        UNITS       "message"
        MAX-ACCESS  read-only
        STATUS      current
        DESCRIPTION "Current number of messages flowed-to-disk
                     Additional info ( nodeType:statistic, assign:msgFtdEnqueues - msgFtdDequeues )"
        ::= { qpid010Broker 31 }

--
-- The BrokerByteFtdDepth data object
--
qpid010BrokerByteFtdDepth OBJECT-TYPE
        SYNTAX      Counter64
        UNITS       "octet"
        MAX-ACCESS  read-only
        STATUS      current
        DESCRIPTION "Current number of bytes flowed-to-disk
                     Additional info ( nodeType:statistic, assign:byteFtdEnqueues - byteFtdDequeues )"
        ::= { qpid010Broker 32 }

--
-- The BrokerReleases data object
--
qpid010BrokerReleases OBJECT-TYPE
        SYNTAX      Counter64
        UNITS       "message"
        MAX-ACCESS  read-only
        STATUS      current
        DESCRIPTION "Acquired messages reinserted into the queue
                     Additional info ( nodeType:statistic )"
        ::= { qpid010Broker 33 }

--
-- The BrokerAcquires data object
--
qpid010BrokerAcquires OBJECT-TYPE
        SYNTAX      Counter64
        UNITS       "message"
        MAX-ACCESS  read-only
        STATUS      current
        DESCRIPTION "Messages acquired from the queue
                     Additional info ( nodeType:statistic )"
        ::= { qpid010Broker 34 }

--
-- The BrokerDiscardsNoRoute data object
--
qpid010BrokerDiscardsNoRoute OBJECT-TYPE
        SYNTAX      Counter64
        UNITS       "message"
        MAX-ACCESS  read-only
        STATUS      current
        DESCRIPTION "Messages discarded due to no-route from exchange
                     Additional info ( nodeType:statistic )"
        ::= { qpid010Broker 35 }

--
-- The BrokerDiscardsTtl data object
--
qpid010BrokerDiscardsTtl OBJECT-TYPE
        SYNTAX      Counter64
        UNITS       "message"
        MAX-ACCESS  read-only
        STATUS      current
        DESCRIPTION "Messages discarded due to TTL expiration
                     Additional info ( nodeType:statistic )"
        ::= { qpid010Broker 36 }

--
-- The BrokerDiscardsRing data object
--
qpid010BrokerDiscardsRing OBJECT-TYPE
        SYNTAX      Counter64
        UNITS       "message"
        MAX-ACCESS  read-only
        STATUS      current
        DESCRIPTION "Messages discarded due to ring-queue overflow
                     Additional info ( nodeType:statistic )"
        ::= { qpid010Broker 37 }

--
-- The BrokerDiscardsLvq data object
--
qpid010BrokerDiscardsLvq OBJECT-TYPE
        SYNTAX      Counter64
        UNITS       "message"
        MAX-ACCESS  read-only
        STATUS      current
        DESCRIPTION "Messages discarded due to LVQ insert
                     Additional info ( nodeType:statistic )"
        ::= { qpid010Broker 38 }

--
-- The BrokerDiscardsOverflow data object
--
qpid010BrokerDiscardsOverflow OBJECT-TYPE
        SYNTAX      Counter64
        UNITS       "message"
        MAX-ACCESS  read-only
        STATUS      current
        DESCRIPTION "Messages discarded due to reject-policy overflow
                     Additional info ( nodeType:statistic )"
        ::= { qpid010Broker 39 }

--
-- The BrokerDiscardsSubscriber data object
--
qpid010BrokerDiscardsSubscriber OBJECT-TYPE
        SYNTAX      Counter64
        UNITS       "message"
        MAX-ACCESS  read-only
        STATUS      current
        DESCRIPTION "Messages discarded due to subscriber reject
                     Additional info ( nodeType:statistic )"
        ::= { qpid010Broker 40 }

--
-- The BrokerDiscardsPurge data object
--
qpid010BrokerDiscardsPurge OBJECT-TYPE
        SYNTAX      Counter64
        UNITS       "message"
        MAX-ACCESS  read-only
        STATUS      current
        DESCRIPTION "Messages discarded due to management purge
                     Additional info ( nodeType:statistic )"
        ::= { qpid010Broker 41 }

--
-- The BrokerReroutes data object
--
qpid010BrokerReroutes OBJECT-TYPE
        SYNTAX      Counter64
        UNITS       "message"
        MAX-ACCESS  read-only
        STATUS      current
        DESCRIPTION "Messages dequeued to management re-route
                     Additional info ( nodeType:statistic )"
        ::= { qpid010Broker 42 }

--
-- The BrokerAbandoned data object
--
qpid010BrokerAbandoned OBJECT-TYPE
        SYNTAX      Counter64
        UNITS       "message"
        MAX-ACCESS  read-only
        STATUS      current
        DESCRIPTION "Messages left in a deleted queue
                     Additional info ( nodeType:statistic )"
        ::= { qpid010Broker 43 }

--
-- The BrokerAbandonedViaAlt data object
--
qpid010BrokerAbandonedViaAlt OBJECT-TYPE
        SYNTAX      Counter64
        UNITS       "message"
        MAX-ACCESS  read-only
        STATUS      current
        DESCRIPTION "Messages routed to alternate exchange from a deleted queue
                     Additional info ( nodeType:statistic )"
        ::= { qpid010Broker 44 }

-- ______________________________________________________________
-- Agent class properties and statistics
-- ______________________________________________________________

--
-- The AgentConnectionRef data object
--
qpid010AgentConnectionRef OBJECT-TYPE
        SYNTAX      ObjId
        MAX-ACCESS  read-only
        STATUS      current
        DESCRIPTION "Agent connectionRef
                     Additional info ( nodeType:property, references:Connection, index:y )"
        ::= { qpid010Agent 1 }

--
-- The AgentLabel data object
--
qpid010AgentLabel OBJECT-TYPE
        SYNTAX      Sstr
        MAX-ACCESS  read-only
        STATUS      current
        DESCRIPTION "Label for agent
                     Additional info ( nodeType:property )"
        ::= { qpid010Agent 2 }

--
-- The AgentRegisteredTo data object
--
qpid010AgentRegisteredTo OBJECT-TYPE
        SYNTAX      ObjId
        MAX-ACCESS  read-only
        STATUS      current
        DESCRIPTION "Broker agent is registered to
                     Additional info ( nodeType:property, references:Broker )"
        ::= { qpid010Agent 3 }

--
-- The AgentSystemId data object
--
qpid010AgentSystemId OBJECT-TYPE
        SYNTAX      Uuid
        MAX-ACCESS  read-only
        STATUS      current
        DESCRIPTION "Identifier of system where agent resides
                     Additional info ( nodeType:property )"
        ::= { qpid010Agent 4 }

--
-- The AgentBrokerBank data object
--
qpid010AgentBrokerBank OBJECT-TYPE
        SYNTAX      Unsigned32
        MAX-ACCESS  read-only
        STATUS      current
        DESCRIPTION "Assigned object-id broker bank
                     Additional info ( nodeType:property )"
        ::= { qpid010Agent 5 }

--
-- The AgentAgentBank data object
--
qpid010AgentAgentBank OBJECT-TYPE
        SYNTAX      Unsigned32
        MAX-ACCESS  read-only
        STATUS      current
        DESCRIPTION "Assigned object-id agent bank
                     Additional info ( nodeType:property )"
        ::= { qpid010Agent 6 }

-- ______________________________________________________________
-- Vhost class table definition
-- ______________________________________________________________
qpid010VhostTable OBJECT-TYPE
        SYNTAX      SEQUENCE OF Qpid010VhostEntry
        MAX-ACCESS  not-accessible
        STATUS      current
        DESCRIPTION "table of vhosts"
        ::= { qpid010Vhosts 1 }
--
-- vhostEntry row definition
--
qpid010VhostEntry OBJECT-TYPE
        SYNTAX      Qpid010VhostEntry
        MAX-ACCESS  not-accessible
        STATUS      current
        DESCRIPTION "A row in the vhost table"
        INDEX { qpid010VhostInternalIndex }
        ::= { qpid010VhostTable 1 }

Qpid010VhostEntry ::= SEQUENCE {
    qpid010VhostBrokerRef                ObjId,
    qpid010VhostName                     Sstr,
    qpid010VhostFederationTag            Sstr,
    qpid010VhostInternalIndex           Unsigned32
}

--
-- qpid010VhostBrokerRef data object
--
qpid010VhostBrokerRef OBJECT-TYPE
        SYNTAX      ObjId
        MAX-ACCESS  read-write
        STATUS      current
        DESCRIPTION "Vhost brokerRef
                     Additional info ( nodeType:property, references:Broker, index:y, parentRef:y )"
        ::= { qpid010VhostEntry 1 }

--
-- qpid010VhostName data object
--
qpid010VhostName OBJECT-TYPE
        SYNTAX      Sstr
        MAX-ACCESS  read-write
        STATUS      current
        DESCRIPTION "Vhost name
                     Additional info ( nodeType:property, index:y )"
        ::= { qpid010VhostEntry 2 }

--
-- qpid010VhostFederationTag data object
--
qpid010VhostFederationTag OBJECT-TYPE
        SYNTAX      Sstr
        MAX-ACCESS  read-only
        STATUS      current
        DESCRIPTION "Vhost federationTag
                     Additional info ( nodeType:property )"
        ::= { qpid010VhostEntry 3 }

--
-- vhostInternalIndex index column
--
qpid010VhostInternalIndex OBJECT-TYPE
        SYNTAX      Unsigned32
        MAX-ACCESS  not-accessible
        STATUS      current
        DESCRIPTION "Internal index for vhost table"
        ::= { qpid010VhostEntry 4 }
-- ______________________________________________________________
-- Queue class table definition
-- ______________________________________________________________
qpid010QueueTable OBJECT-TYPE
        SYNTAX      SEQUENCE OF Qpid010QueueEntry
        MAX-ACCESS  not-accessible
        STATUS      current
        DESCRIPTION "table of queues"
        ::= { qpid010Queues 1 }
--
-- queueEntry row definition
--
qpid010QueueEntry OBJECT-TYPE
        SYNTAX      Qpid010QueueEntry
        MAX-ACCESS  not-accessible
        STATUS      current
        DESCRIPTION "A row in the queue table"
        INDEX { qpid010QueueInternalIndex }
        ::= { qpid010QueueTable 1 }

Qpid010QueueEntry ::= SEQUENCE {
    qpid010QueueVhostRef                 ObjId,
    qpid010QueueName                     Sstr,
    qpid010QueueDurable                  TruthValue,
    qpid010QueueAutoDelete               TruthValue,
    qpid010QueueExclusive                TruthValue,
    qpid010QueueArguments                Map,
    qpid010QueueAltExchange              ObjId,
    qpid010QueueMsgTotalEnqueues         Counter64,
    qpid010QueueMsgTotalDequeues         Counter64,
    qpid010QueueMsgTxnEnqueues           Counter64,
    qpid010QueueMsgTxnDequeues           Counter64,
    qpid010QueueMsgPersistEnqueues       Counter64,
    qpid010QueueMsgPersistDequeues       Counter64,
    qpid010QueueMsgDepth                 Counter64,
    qpid010QueueByteDepth                Counter64,
    qpid010QueueByteTotalEnqueues        Counter64,
    qpid010QueueByteTotalDequeues        Counter64,
    qpid010QueueByteTxnEnqueues          Counter64,
    qpid010QueueByteTxnDequeues          Counter64,
    qpid010QueueBytePersistEnqueues      Counter64,
    qpid010QueueBytePersistDequeues      Counter64,
    qpid010QueueMsgFtdEnqueues           Counter64,
    qpid010QueueMsgFtdDequeues           Counter64,
    qpid010QueueByteFtdEnqueues          Counter64,
    qpid010QueueByteFtdDequeues          Counter64,
    qpid010QueueMsgFtdDepth              Counter64,
    qpid010QueueByteFtdDepth             Counter64,
    qpid010QueueReleases                 Counter64,
    qpid010QueueAcquires                 Counter64,
    qpid010QueueDiscardsTtl              Counter64,
    qpid010QueueDiscardsRing             Counter64,
    qpid010QueueDiscardsLvq              Counter64,
    qpid010QueueDiscardsOverflow         Counter64,
    qpid010QueueDiscardsSubscriber       Counter64,
    qpid010QueueDiscardsPurge            Counter64,
    qpid010QueueReroutes                 Counter64,
    qpid010QueueConsumerCount            Hilo32,
    qpid010QueueConsumerCountHi          Hilo32,
    qpid010QueueConsumerCountLow         Hilo32,
    qpid010QueueBindingCount             Hilo32,
    qpid010QueueBindingCountHi           Hilo32,
    qpid010QueueBindingCountLow          Hilo32,
    qpid010QueueUnackedMessages          Hilo32,
    qpid010QueueUnackedMessagesHi        Hilo32,
    qpid010QueueUnackedMessagesLow       Hilo32,
    qpid010QueueMessageLatency           TimeTicks,
    qpid010QueueFlowStopped              TruthValue,
    qpid010QueueFlowStoppedCount         Counter32,
    qpid010QueueInternalIndex           Unsigned32
}

--
-- qpid010QueueVhostRef data object
--
qpid010QueueVhostRef OBJECT-TYPE
        SYNTAX      ObjId
        MAX-ACCESS  read-write
        STATUS      current
        DESCRIPTION "Queue vhostRef
                     Additional info ( nodeType:property, references:Vhost, index:y, parentRef:y )"
        ::= { qpid010QueueEntry 1 }

--
-- qpid010QueueName data object
--
qpid010QueueName OBJECT-TYPE
        SYNTAX      Sstr
        MAX-ACCESS  read-write
        STATUS      current
        DESCRIPTION "Queue name
                     Additional info ( nodeType:property, index:y )"
        ::= { qpid010QueueEntry 2 }

--
-- qpid010QueueDurable data object
--
qpid010QueueDurable OBJECT-TYPE
        SYNTAX      TruthValue
        MAX-ACCESS  read-write
        STATUS      current
        DESCRIPTION "Queue durable
                     Additional info ( nodeType:property )"
        ::= { qpid010QueueEntry 3 }

--
-- qpid010QueueAutoDelete data object
--
qpid010QueueAutoDelete OBJECT-TYPE
        SYNTAX      TruthValue
        MAX-ACCESS  read-write
        STATUS      current
        DESCRIPTION "Queue autoDelete
                     Additional info ( nodeType:property )"
        ::= { qpid010QueueEntry 4 }

--
-- qpid010QueueExclusive data object
--
qpid010QueueExclusive OBJECT-TYPE
        SYNTAX      TruthValue
        MAX-ACCESS  read-write
        STATUS      current
        DESCRIPTION "Queue exclusive
                     Additional info ( nodeType:property )"
        ::= { qpid010QueueEntry 5 }

--
-- qpid010QueueArguments data object
--
qpid010QueueArguments OBJECT-TYPE
        SYNTAX      Map
        MAX-ACCESS  read-only
        STATUS      current
        DESCRIPTION "Arguments supplied in queue.declare
                     Additional info ( nodeType:property )"
        ::= { qpid010QueueEntry 6 }

--
-- qpid010QueueAltExchange data object
--
qpid010QueueAltExchange OBJECT-TYPE
        SYNTAX      ObjId
        MAX-ACCESS  read-only
        STATUS      current
        DESCRIPTION "Queue altExchange
                     Additional info ( nodeType:property, references:Exchange, optional:y )"
        ::= { qpid010QueueEntry 7 }

--
-- qpid010QueueMsgTotalEnqueues data object
--
qpid010QueueMsgTotalEnqueues OBJECT-TYPE
        SYNTAX      Counter64
        UNITS       "message"
        MAX-ACCESS  read-only
        STATUS      current
        DESCRIPTION "Total messages enqueued
                     Additional info ( nodeType:statistic )"
        ::= { qpid010QueueEntry 8 }

--
-- qpid010QueueMsgTotalDequeues data object
--
qpid010QueueMsgTotalDequeues OBJECT-TYPE
        SYNTAX      Counter64
        UNITS       "message"
        MAX-ACCESS  read-only
        STATUS      current
        DESCRIPTION "Total messages dequeued
                     Additional info ( nodeType:statistic )"
        ::= { qpid010QueueEntry 9 }

--
-- qpid010QueueMsgTxnEnqueues data object
--
qpid010QueueMsgTxnEnqueues OBJECT-TYPE
        SYNTAX      Counter64
        UNITS       "message"
        MAX-ACCESS  read-only
        STATUS      current
        DESCRIPTION "Transactional messages enqueued
                     Additional info ( nodeType:statistic )"
        ::= { qpid010QueueEntry 10 }

--
-- qpid010QueueMsgTxnDequeues data object
--
qpid010QueueMsgTxnDequeues OBJECT-TYPE
        SYNTAX      Counter64
        UNITS       "message"
        MAX-ACCESS  read-only
        STATUS      current
        DESCRIPTION "Transactional messages dequeued
                     Additional info ( nodeType:statistic )"
        ::= { qpid010QueueEntry 11 }

--
-- qpid010QueueMsgPersistEnqueues data object
--
qpid010QueueMsgPersistEnqueues OBJECT-TYPE
        SYNTAX      Counter64
        UNITS       "message"
        MAX-ACCESS  read-only
        STATUS      current
        DESCRIPTION "Persistent messages enqueued
                     Additional info ( nodeType:statistic )"
        ::= { qpid010QueueEntry 12 }

--
-- qpid010QueueMsgPersistDequeues data object
--
qpid010QueueMsgPersistDequeues OBJECT-TYPE
        SYNTAX      Counter64
        UNITS       "message"
        MAX-ACCESS  read-only
        STATUS      current
        DESCRIPTION "Persistent messages dequeued
                     Additional info ( nodeType:statistic )"
        ::= { qpid010QueueEntry 13 }

--
-- qpid010QueueMsgDepth data object
--
qpid010QueueMsgDepth OBJECT-TYPE
        SYNTAX      Counter64
        UNITS       "message"
        MAX-ACCESS  read-only
        STATUS      current
        DESCRIPTION "Current size of queue in messages
                     Additional info ( nodeType:statistic, assign:msgTotalEnqueues - msgTotalDequeues )"
        ::= { qpid010QueueEntry 14 }

--
-- qpid010QueueByteDepth data object
--
qpid010QueueByteDepth OBJECT-TYPE
        SYNTAX      Counter64
        UNITS       "octet"
        MAX-ACCESS  read-only
        STATUS      current
        DESCRIPTION "Current size of queue in bytes
                     Additional info ( nodeType:statistic, assign:byteTotalEnqueues - byteTotalDequeues )"
        ::= { qpid010QueueEntry 15 }

--
-- qpid010QueueByteTotalEnqueues data object
--
qpid010QueueByteTotalEnqueues OBJECT-TYPE
        SYNTAX      Counter64
        UNITS       "octet"
        MAX-ACCESS  read-only
        STATUS      current
        DESCRIPTION "Total messages enqueued
                     Additional info ( nodeType:statistic )"
        ::= { qpid010QueueEntry 16 }

--
-- qpid010QueueByteTotalDequeues data object
--
qpid010QueueByteTotalDequeues OBJECT-TYPE
        SYNTAX      Counter64
        UNITS       "octet"
        MAX-ACCESS  read-only
        STATUS      current
        DESCRIPTION "Total messages dequeued
                     Additional info ( nodeType:statistic )"
        ::= { qpid010QueueEntry 17 }

--
-- qpid010QueueByteTxnEnqueues data object
--
qpid010QueueByteTxnEnqueues OBJECT-TYPE
        SYNTAX      Counter64
        UNITS       "octet"
        MAX-ACCESS  read-only
        STATUS      current
        DESCRIPTION "Transactional messages enqueued
                     Additional info ( nodeType:statistic )"
        ::= { qpid010QueueEntry 18 }

--
-- qpid010QueueByteTxnDequeues data object
--
qpid010QueueByteTxnDequeues OBJECT-TYPE
        SYNTAX      Counter64
        UNITS       "octet"
        MAX-ACCESS  read-only
        STATUS      current
        DESCRIPTION "Transactional messages dequeued
                     Additional info ( nodeType:statistic )"
        ::= { qpid010QueueEntry 19 }

--
-- qpid010QueueBytePersistEnqueues data object
--
qpid010QueueBytePersistEnqueues OBJECT-TYPE
        SYNTAX      Counter64
        UNITS       "octet"
        MAX-ACCESS  read-only
        STATUS      current
        DESCRIPTION "Persistent messages enqueued
                     Additional info ( nodeType:statistic )"
        ::= { qpid010QueueEntry 20 }

--
-- qpid010QueueBytePersistDequeues data object
--
qpid010QueueBytePersistDequeues OBJECT-TYPE
        SYNTAX      Counter64
        UNITS       "octet"
        MAX-ACCESS  read-only
        STATUS      current
        DESCRIPTION "Persistent messages dequeued
                     Additional info ( nodeType:statistic )"
        ::= { qpid010QueueEntry 21 }

--
-- qpid010QueueMsgFtdEnqueues data object
--
qpid010QueueMsgFtdEnqueues OBJECT-TYPE
        SYNTAX      Counter64
        UNITS       "message"
        MAX-ACCESS  read-only
        STATUS      current
        DESCRIPTION "Total message bodies released from memory and flowed-to-disk on broker
                     Additional info ( nodeType:statistic )"
        ::= { qpid010QueueEntry 22 }

--
-- qpid010QueueMsgFtdDequeues data object
--
qpid010QueueMsgFtdDequeues OBJECT-TYPE
        SYNTAX      Counter64
        UNITS       "message"
        MAX-ACCESS  read-only
        STATUS      current
        DESCRIPTION "Total message bodies dequeued from the broker having been flowed-to-disk
                     Additional info ( nodeType:statistic )"
        ::= { qpid010QueueEntry 23 }

--
-- qpid010QueueByteFtdEnqueues data object
--
qpid010QueueByteFtdEnqueues OBJECT-TYPE
        SYNTAX      Counter64
        UNITS       "octet"
        MAX-ACCESS  read-only
        STATUS      current
        DESCRIPTION "Total bytes released from memory and flowed-to-disk on broker
                     Additional info ( nodeType:statistic )"
        ::= { qpid010QueueEntry 24 }

--
-- qpid010QueueByteFtdDequeues data object
--
qpid010QueueByteFtdDequeues OBJECT-TYPE
        SYNTAX      Counter64
        UNITS       "octet"
        MAX-ACCESS  read-only
        STATUS      current
        DESCRIPTION "Total bytes dequeued from the broker having been flowed-to-disk
                     Additional info ( nodeType:statistic )"
        ::= { qpid010QueueEntry 25 }

--
-- qpid010QueueMsgFtdDepth data object
--
qpid010QueueMsgFtdDepth OBJECT-TYPE
        SYNTAX      Counter64
        UNITS       "message"
        MAX-ACCESS  read-only
        STATUS      current
        DESCRIPTION "Current number of messages flowed-to-disk
                     Additional info ( nodeType:statistic, assign:msgFtdEnqueues - msgFtdDequeues )"
        ::= { qpid010QueueEntry 26 }

--
-- qpid010QueueByteFtdDepth data object
--
qpid010QueueByteFtdDepth OBJECT-TYPE
        SYNTAX      Counter64
        UNITS       "octet"
        MAX-ACCESS  read-only
        STATUS      current
        DESCRIPTION "Current number of bytes flowed-to-disk
                     Additional info ( nodeType:statistic, assign:byteFtdEnqueues - byteFtdDequeues )"
        ::= { qpid010QueueEntry 27 }

--
-- qpid010QueueReleases data object
--
qpid010QueueReleases OBJECT-TYPE
        SYNTAX      Counter64
        UNITS       "message"
        MAX-ACCESS  read-only
        STATUS      current
        DESCRIPTION "Acquired messages reinserted into the queue
                     Additional info ( nodeType:statistic )"
        ::= { qpid010QueueEntry 28 }

--
-- qpid010QueueAcquires data object
--
qpid010QueueAcquires OBJECT-TYPE
        SYNTAX      Counter64
        UNITS       "message"
        MAX-ACCESS  read-only
        STATUS      current
        DESCRIPTION "Messages acquired from the queue
                     Additional info ( nodeType:statistic )"
        ::= { qpid010QueueEntry 29 }

--
-- qpid010QueueDiscardsTtl data object
--
qpid010QueueDiscardsTtl OBJECT-TYPE
        SYNTAX      Counter64
        UNITS       "message"
        MAX-ACCESS  read-only
        STATUS      current
        DESCRIPTION "Messages discarded due to TTL expiration
                     Additional info ( nodeType:statistic )"
        ::= { qpid010QueueEntry 30 }

--
-- qpid010QueueDiscardsRing data object
--
qpid010QueueDiscardsRing OBJECT-TYPE
        SYNTAX      Counter64
        UNITS       "message"
        MAX-ACCESS  read-only
        STATUS      current
        DESCRIPTION "Messages discarded due to ring-queue overflow
                     Additional info ( nodeType:statistic )"
        ::= { qpid010QueueEntry 31 }

--
-- qpid010QueueDiscardsLvq data object
--
qpid010QueueDiscardsLvq OBJECT-TYPE
        SYNTAX      Counter64
        UNITS       "message"
        MAX-ACCESS  read-only
        STATUS      current
        DESCRIPTION "Messages discarded due to LVQ insert
                     Additional info ( nodeType:statistic )"
        ::= { qpid010QueueEntry 32 }

--
-- qpid010QueueDiscardsOverflow data object
--
qpid010QueueDiscardsOverflow OBJECT-TYPE
        SYNTAX      Counter64
        UNITS       "message"
        MAX-ACCESS  read-only
        STATUS      current
        DESCRIPTION "Messages discarded due to reject-policy overflow
                     Additional info ( nodeType:statistic )"
        ::= { qpid010QueueEntry 33 }

--
-- qpid010QueueDiscardsSubscriber data object
--
qpid010QueueDiscardsSubscriber OBJECT-TYPE
        SYNTAX      Counter64
        UNITS       "message"
        MAX-ACCESS  read-only
        STATUS      current
        DESCRIPTION "Messages discarded due to subscriber reject
                     Additional info ( nodeType:statistic )"
        ::= { qpid010QueueEntry 34 }

--
-- qpid010QueueDiscardsPurge data object
--
qpid010QueueDiscardsPurge OBJECT-TYPE
        SYNTAX      Counter64
        UNITS       "message"
        MAX-ACCESS  read-only
        STATUS      current
        DESCRIPTION "Messages discarded due to management purge
                     Additional info ( nodeType:statistic )"
        ::= { qpid010QueueEntry 35 }

--
-- qpid010QueueReroutes data object
--
qpid010QueueReroutes OBJECT-TYPE
        SYNTAX      Counter64
        UNITS       "message"
        MAX-ACCESS  read-only
        STATUS      current
        DESCRIPTION "Messages dequeued to management re-route
                     Additional info ( nodeType:statistic )"
        ::= { qpid010QueueEntry 36 }

--
-- qpid010QueueConsumerCount data object
--
qpid010QueueConsumerCount OBJECT-TYPE
        SYNTAX      Hilo32
        UNITS       "consumer"
        MAX-ACCESS  read-only
        STATUS      current
        DESCRIPTION "Current consumers on queue
                     Additional info ( nodeType:statistic )"
        ::= { qpid010QueueEntry 37 }

--
-- qpid010QueueConsumerCountHi data object
--
qpid010QueueConsumerCountHi OBJECT-TYPE
        SYNTAX      Hilo32
        UNITS       "consumer"
        MAX-ACCESS  read-only
        STATUS      current
        DESCRIPTION "Current consumers on queue
                     Additional info ( nodeType:statistic )"
        ::= { qpid010QueueEntry 38 }

--
-- qpid010QueueConsumerCountLow data object
--
qpid010QueueConsumerCountLow OBJECT-TYPE
        SYNTAX      Hilo32
        UNITS       "consumer"
        MAX-ACCESS  read-only
        STATUS      current
        DESCRIPTION "Current consumers on queue
                     Additional info ( nodeType:statistic )"
        ::= { qpid010QueueEntry 39 }

--
-- qpid010QueueBindingCount data object
--
qpid010QueueBindingCount OBJECT-TYPE
        SYNTAX      Hilo32
        UNITS       "binding"
        MAX-ACCESS  read-only
        STATUS      current
        DESCRIPTION "Current bindings
                     Additional info ( nodeType:statistic )"
        ::= { qpid010QueueEntry 40 }

--
-- qpid010QueueBindingCountHi data object
--
qpid010QueueBindingCountHi OBJECT-TYPE
        SYNTAX      Hilo32
        UNITS       "binding"
        MAX-ACCESS  read-only
        STATUS      current
        DESCRIPTION "Current bindings
                     Additional info ( nodeType:statistic )"
        ::= { qpid010QueueEntry 41 }

--
-- qpid010QueueBindingCountLow data object
--
qpid010QueueBindingCountLow OBJECT-TYPE
        SYNTAX      Hilo32
        UNITS       "binding"
        MAX-ACCESS  read-only
        STATUS      current
        DESCRIPTION "Current bindings
                     Additional info ( nodeType:statistic )"
        ::= { qpid010QueueEntry 42 }

--
-- qpid010QueueUnackedMessages data object
--
qpid010QueueUnackedMessages OBJECT-TYPE
        SYNTAX      Hilo32
        UNITS       "message"
        MAX-ACCESS  read-only
        STATUS      current
        DESCRIPTION "Messages consumed but not yet acked
                     Additional info ( nodeType:statistic )"
        ::= { qpid010QueueEntry 43 }

--
-- qpid010QueueUnackedMessagesHi data object
--
qpid010QueueUnackedMessagesHi OBJECT-TYPE
        SYNTAX      Hilo32
        UNITS       "message"
        MAX-ACCESS  read-only
        STATUS      current
        DESCRIPTION "Messages consumed but not yet acked
                     Additional info ( nodeType:statistic )"
        ::= { qpid010QueueEntry 44 }

--
-- qpid010QueueUnackedMessagesLow data object
--
qpid010QueueUnackedMessagesLow OBJECT-TYPE
        SYNTAX      Hilo32
        UNITS       "message"
        MAX-ACCESS  read-only
        STATUS      current
        DESCRIPTION "Messages consumed but not yet acked
                     Additional info ( nodeType:statistic )"
        ::= { qpid010QueueEntry 45 }

--
-- qpid010QueueMessageLatency data object
--
qpid010QueueMessageLatency OBJECT-TYPE
        SYNTAX      TimeTicks
        UNITS       "nanosecond"
        MAX-ACCESS  read-only
        STATUS      current
        DESCRIPTION "Broker latency through this queue
                     Additional info ( nodeType:statistic )"
        ::= { qpid010QueueEntry 46 }

--
-- qpid010QueueFlowStopped data object
--
qpid010QueueFlowStopped OBJECT-TYPE
        SYNTAX      TruthValue
        MAX-ACCESS  read-only
        STATUS      current
        DESCRIPTION "Flow control active.
                     Additional info ( nodeType:statistic )"
        ::= { qpid010QueueEntry 47 }

--
-- qpid010QueueFlowStoppedCount data object
--
qpid010QueueFlowStoppedCount OBJECT-TYPE
        SYNTAX      Counter32
        MAX-ACCESS  read-only
        STATUS      current
        DESCRIPTION "Number of times flow control was activated for this queue
                     Additional info ( nodeType:statistic )"
        ::= { qpid010QueueEntry 48 }

--
-- queueInternalIndex index column
--
qpid010QueueInternalIndex OBJECT-TYPE
        SYNTAX      Unsigned32
        MAX-ACCESS  not-accessible
        STATUS      current
        DESCRIPTION "Internal index for queue table"
        ::= { qpid010QueueEntry 49 }
-- ______________________________________________________________
-- Exchange class table definition
-- ______________________________________________________________
qpid010ExchangeTable OBJECT-TYPE
        SYNTAX      SEQUENCE OF Qpid010ExchangeEntry
        MAX-ACCESS  not-accessible
        STATUS      current
        DESCRIPTION "table of exchanges"
        ::= { qpid010Exchanges 1 }
--
-- exchangeEntry row definition
--
qpid010ExchangeEntry OBJECT-TYPE
        SYNTAX      Qpid010ExchangeEntry
        MAX-ACCESS  not-accessible
        STATUS      current
        DESCRIPTION "A row in the exchange table"
        INDEX { qpid010ExchangeInternalIndex }
        ::= { qpid010ExchangeTable 1 }

Qpid010ExchangeEntry ::= SEQUENCE {
    qpid010ExchangeVhostRef              ObjId,
    qpid010ExchangeName                  Sstr,
    qpid010ExchangeType                  Sstr,
    qpid010ExchangeDurable               TruthValue,
    qpid010ExchangeAutoDelete            TruthValue,
    qpid010ExchangeAltExchange           ObjId,
    qpid010ExchangeArguments             Map,
    qpid010ExchangeProducerCount         Hilo32,
    qpid010ExchangeProducerCountHi       Hilo32,
    qpid010ExchangeProducerCountLow      Hilo32,
    qpid010ExchangeBindingCount          Hilo32,
    qpid010ExchangeBindingCountHi        Hilo32,
    qpid010ExchangeBindingCountLow       Hilo32,
    qpid010ExchangeMsgReceives           Counter64,
    qpid010ExchangeMsgDrops              Counter64,
    qpid010ExchangeMsgRoutes             Counter64,
    qpid010ExchangeByteReceives          Counter64,
    qpid010ExchangeByteDrops             Counter64,
    qpid010ExchangeByteRoutes            Counter64,
    qpid010ExchangeInternalIndex           Unsigned32
}

--
-- qpid010ExchangeVhostRef data object
--
qpid010ExchangeVhostRef OBJECT-TYPE
        SYNTAX      ObjId
        MAX-ACCESS  read-write
        STATUS      current
        DESCRIPTION "Exchange vhostRef
                     Additional info ( nodeType:property, references:Vhost, index:y, parentRef:y )"
        ::= { qpid010ExchangeEntry 1 }

--
-- qpid010ExchangeName data object
--
qpid010ExchangeName OBJECT-TYPE
        SYNTAX      Sstr
        MAX-ACCESS  read-write
        STATUS      current
        DESCRIPTION "Exchange name
                     Additional info ( nodeType:property, index:y )"
        ::= { qpid010ExchangeEntry 2 }

--
-- qpid010ExchangeType data object
--
qpid010ExchangeType OBJECT-TYPE
        SYNTAX      Sstr
        MAX-ACCESS  read-only
        STATUS      current
        DESCRIPTION "Exchange type
                     Additional info ( nodeType:property )"
        ::= { qpid010ExchangeEntry 3 }

--
-- qpid010ExchangeDurable data object
--
qpid010ExchangeDurable OBJECT-TYPE
        SYNTAX      TruthValue
        MAX-ACCESS  read-only
        STATUS      current
        DESCRIPTION "Exchange durable
                     Additional info ( nodeType:property )"
        ::= { qpid010ExchangeEntry 4 }

--
-- qpid010ExchangeAutoDelete data object
--
qpid010ExchangeAutoDelete OBJECT-TYPE
        SYNTAX      TruthValue
        MAX-ACCESS  read-only
        STATUS      current
        DESCRIPTION "Exchange autoDelete
                     Additional info ( nodeType:property )"
        ::= { qpid010ExchangeEntry 5 }

--
-- qpid010ExchangeAltExchange data object
--
qpid010ExchangeAltExchange OBJECT-TYPE
        SYNTAX      ObjId
        MAX-ACCESS  read-only
        STATUS      current
        DESCRIPTION "Exchange altExchange
                     Additional info ( nodeType:property, references:Exchange, optional:y )"
        ::= { qpid010ExchangeEntry 6 }

--
-- qpid010ExchangeArguments data object
--
qpid010ExchangeArguments OBJECT-TYPE
        SYNTAX      Map
        MAX-ACCESS  read-only
        STATUS      current
        DESCRIPTION "Arguments supplied in exchange.declare
                     Additional info ( nodeType:property )"
        ::= { qpid010ExchangeEntry 7 }

--
-- qpid010ExchangeProducerCount data object
--
qpid010ExchangeProducerCount OBJECT-TYPE
        SYNTAX      Hilo32
        MAX-ACCESS  read-only
        STATUS      current
        DESCRIPTION "Current producers on exchange
                     Additional info ( nodeType:statistic )"
        ::= { qpid010ExchangeEntry 8 }

--
-- qpid010ExchangeProducerCountHi data object
--
qpid010ExchangeProducerCountHi OBJECT-TYPE
        SYNTAX      Hilo32
        MAX-ACCESS  read-only
        STATUS      current
        DESCRIPTION "Current producers on exchange
                     Additional info ( nodeType:statistic )"
        ::= { qpid010ExchangeEntry 9 }

--
-- qpid010ExchangeProducerCountLow data object
--
qpid010ExchangeProducerCountLow OBJECT-TYPE
        SYNTAX      Hilo32
        MAX-ACCESS  read-only
        STATUS      current
        DESCRIPTION "Current producers on exchange
                     Additional info ( nodeType:statistic )"
        ::= { qpid010ExchangeEntry 10 }

--
-- qpid010ExchangeBindingCount data object
--
qpid010ExchangeBindingCount OBJECT-TYPE
        SYNTAX      Hilo32
        MAX-ACCESS  read-only
        STATUS      current
        DESCRIPTION "Current bindings
                     Additional info ( nodeType:statistic )"
        ::= { qpid010ExchangeEntry 11 }

--
-- qpid010ExchangeBindingCountHi data object
--
qpid010ExchangeBindingCountHi OBJECT-TYPE
        SYNTAX      Hilo32
        MAX-ACCESS  read-only
        STATUS      current
        DESCRIPTION "Current bindings
                     Additional info ( nodeType:statistic )"
        ::= { qpid010ExchangeEntry 12 }

--
-- qpid010ExchangeBindingCountLow data object
--
qpid010ExchangeBindingCountLow OBJECT-TYPE
        SYNTAX      Hilo32
        MAX-ACCESS  read-only
        STATUS      current
        DESCRIPTION "Current bindings
                     Additional info ( nodeType:statistic )"
        ::= { qpid010ExchangeEntry 13 }

--
-- qpid010ExchangeMsgReceives data object
--
qpid010ExchangeMsgReceives OBJECT-TYPE
        SYNTAX      Counter64
        MAX-ACCESS  read-only
        STATUS      current
        DESCRIPTION "Total messages received
                     Additional info ( nodeType:statistic )"
        ::= { qpid010ExchangeEntry 14 }

--
-- qpid010ExchangeMsgDrops data object
--
qpid010ExchangeMsgDrops OBJECT-TYPE
        SYNTAX      Counter64
        MAX-ACCESS  read-only
        STATUS      current
        DESCRIPTION "Total messages dropped (no matching key)
                     Additional info ( nodeType:statistic )"
        ::= { qpid010ExchangeEntry 15 }

--
-- qpid010ExchangeMsgRoutes data object
--
qpid010ExchangeMsgRoutes OBJECT-TYPE
        SYNTAX      Counter64
        MAX-ACCESS  read-only
        STATUS      current
        DESCRIPTION "Total routed messages
                     Additional info ( nodeType:statistic )"
        ::= { qpid010ExchangeEntry 16 }

--
-- qpid010ExchangeByteReceives data object
--
qpid010ExchangeByteReceives OBJECT-TYPE
        SYNTAX      Counter64
        MAX-ACCESS  read-only
        STATUS      current
        DESCRIPTION "Total bytes received
                     Additional info ( nodeType:statistic )"
        ::= { qpid010ExchangeEntry 17 }

--
-- qpid010ExchangeByteDrops data object
--
qpid010ExchangeByteDrops OBJECT-TYPE
        SYNTAX      Counter64
        MAX-ACCESS  read-only
        STATUS      current
        DESCRIPTION "Total bytes dropped (no matching key)
                     Additional info ( nodeType:statistic )"
        ::= { qpid010ExchangeEntry 18 }

--
-- qpid010ExchangeByteRoutes data object
--
qpid010ExchangeByteRoutes OBJECT-TYPE
        SYNTAX      Counter64
        MAX-ACCESS  read-only
        STATUS      current
        DESCRIPTION "Total routed bytes
                     Additional info ( nodeType:statistic )"
        ::= { qpid010ExchangeEntry 19 }

--
-- exchangeInternalIndex index column
--
qpid010ExchangeInternalIndex OBJECT-TYPE
        SYNTAX      Unsigned32
        MAX-ACCESS  not-accessible
        STATUS      current
        DESCRIPTION "Internal index for exchange table"
        ::= { qpid010ExchangeEntry 20 }
-- ______________________________________________________________
-- Binding class table definition
-- ______________________________________________________________
qpid010BindingTable OBJECT-TYPE
        SYNTAX      SEQUENCE OF Qpid010BindingEntry
        MAX-ACCESS  not-accessible
        STATUS      current
        DESCRIPTION "table of bindings"
        ::= { qpid010Bindings 1 }
--
-- bindingEntry row definition
--
qpid010BindingEntry OBJECT-TYPE
        SYNTAX      Qpid010BindingEntry
        MAX-ACCESS  not-accessible
        STATUS      current
        DESCRIPTION "A row in the binding table"
        INDEX { qpid010BindingInternalIndex }
        ::= { qpid010BindingTable 1 }

Qpid010BindingEntry ::= SEQUENCE {
    qpid010BindingExchangeRef            ObjId,
    qpid010BindingQueueRef               ObjId,
    qpid010BindingBindingKey             Lstr,
    qpid010BindingArguments              Map,
    qpid010BindingOrigin                 Sstr,
    qpid010BindingMsgMatched             Counter64,
    qpid010BindingInternalIndex           Unsigned32
}

--
-- qpid010BindingExchangeRef data object
--
qpid010BindingExchangeRef OBJECT-TYPE
        SYNTAX      ObjId
        MAX-ACCESS  read-write
        STATUS      current
        DESCRIPTION "Binding exchangeRef
                     Additional info ( nodeType:property, references:Exchange, index:y, parentRef:y )"
        ::= { qpid010BindingEntry 1 }

--
-- qpid010BindingQueueRef data object
--
qpid010BindingQueueRef OBJECT-TYPE
        SYNTAX      ObjId
        MAX-ACCESS  read-write
        STATUS      current
        DESCRIPTION "Binding queueRef
                     Additional info ( nodeType:property, references:Queue, index:y )"
        ::= { qpid010BindingEntry 2 }

--
-- qpid010BindingBindingKey data object
--
qpid010BindingBindingKey OBJECT-TYPE
        SYNTAX      Lstr
        MAX-ACCESS  read-write
        STATUS      current
        DESCRIPTION "Binding bindingKey
                     Additional info ( nodeType:property, index:y )"
        ::= { qpid010BindingEntry 3 }

--
-- qpid010BindingArguments data object
--
qpid010BindingArguments OBJECT-TYPE
        SYNTAX      Map
        MAX-ACCESS  read-write
        STATUS      current
        DESCRIPTION "Binding arguments
                     Additional info ( nodeType:property )"
        ::= { qpid010BindingEntry 4 }

--
-- qpid010BindingOrigin data object
--
qpid010BindingOrigin OBJECT-TYPE
        SYNTAX      Sstr
        MAX-ACCESS  read-only
        STATUS      current
        DESCRIPTION "Binding origin
                     Additional info ( nodeType:property, optional:y )"
        ::= { qpid010BindingEntry 5 }

--
-- qpid010BindingMsgMatched data object
--
qpid010BindingMsgMatched OBJECT-TYPE
        SYNTAX      Counter64
        MAX-ACCESS  read-only
        STATUS      current
        DESCRIPTION "Binding msgMatched
                     Additional info ( nodeType:statistic )"
        ::= { qpid010BindingEntry 6 }

--
-- bindingInternalIndex index column
--
qpid010BindingInternalIndex OBJECT-TYPE
        SYNTAX      Unsigned32
        MAX-ACCESS  not-accessible
        STATUS      current
        DESCRIPTION "Internal index for binding table"
        ::= { qpid010BindingEntry 7 }
-- ______________________________________________________________
-- Subscription class table definition
-- ______________________________________________________________
qpid010SubscriptionTable OBJECT-TYPE
        SYNTAX      SEQUENCE OF Qpid010SubscriptionEntry
        MAX-ACCESS  not-accessible
        STATUS      current
        DESCRIPTION "table of subscriptions"
        ::= { qpid010Subscriptions 1 }
--
-- subscriptionEntry row definition
--
qpid010SubscriptionEntry OBJECT-TYPE
        SYNTAX      Qpid010SubscriptionEntry
        MAX-ACCESS  not-accessible
        STATUS      current
        DESCRIPTION "A row in the subscription table"
        INDEX { qpid010SubscriptionInternalIndex }
        ::= { qpid010SubscriptionTable 1 }

Qpid010SubscriptionEntry ::= SEQUENCE {
    qpid010SubscriptionSessionRef        ObjId,
    qpid010SubscriptionQueueRef          ObjId,
    qpid010SubscriptionName              Sstr,
    qpid010SubscriptionBrowsing          TruthValue,
    qpid010SubscriptionAcknowledged      TruthValue,
    qpid010SubscriptionExclusive         TruthValue,
    qpid010SubscriptionCreditMode        Sstr,
    qpid010SubscriptionArguments         Map,
    qpid010SubscriptionDelivered         Counter64,
    qpid010SubscriptionInternalIndex           Unsigned32
}

--
-- qpid010SubscriptionSessionRef data object
--
qpid010SubscriptionSessionRef OBJECT-TYPE
        SYNTAX      ObjId
        MAX-ACCESS  read-write
        STATUS      current
        DESCRIPTION "Subscription sessionRef
                     Additional info ( nodeType:property, references:Session, index:y, parentRef:y )"
        ::= { qpid010SubscriptionEntry 1 }

--
-- qpid010SubscriptionQueueRef data object
--
qpid010SubscriptionQueueRef OBJECT-TYPE
        SYNTAX      ObjId
        MAX-ACCESS  read-write
        STATUS      current
        DESCRIPTION "Subscription queueRef
                     Additional info ( nodeType:property, references:Queue, index:y )"
        ::= { qpid010SubscriptionEntry 2 }

--
-- qpid010SubscriptionName data object
--
qpid010SubscriptionName OBJECT-TYPE
        SYNTAX      Sstr
        MAX-ACCESS  read-write
        STATUS      current
        DESCRIPTION "Subscription name
                     Additional info ( nodeType:property, index:y )"
        ::= { qpid010SubscriptionEntry 3 }

--
-- qpid010SubscriptionBrowsing data object
--
qpid010SubscriptionBrowsing OBJECT-TYPE
        SYNTAX      TruthValue
        MAX-ACCESS  read-write
        STATUS      current
        DESCRIPTION "Subscription browsing
                     Additional info ( nodeType:property )"
        ::= { qpid010SubscriptionEntry 4 }

--
-- qpid010SubscriptionAcknowledged data object
--
qpid010SubscriptionAcknowledged OBJECT-TYPE
        SYNTAX      TruthValue
        MAX-ACCESS  read-write
        STATUS      current
        DESCRIPTION "Subscription acknowledged
                     Additional info ( nodeType:property )"
        ::= { qpid010SubscriptionEntry 5 }

--
-- qpid010SubscriptionExclusive data object
--
qpid010SubscriptionExclusive OBJECT-TYPE
        SYNTAX      TruthValue
        MAX-ACCESS  read-write
        STATUS      current
        DESCRIPTION "Subscription exclusive
                     Additional info ( nodeType:property )"
        ::= { qpid010SubscriptionEntry 6 }

--
-- qpid010SubscriptionCreditMode data object
--
qpid010SubscriptionCreditMode OBJECT-TYPE
        SYNTAX      Sstr
        MAX-ACCESS  read-only
        STATUS      current
        DESCRIPTION "WINDOW or CREDIT
                     Additional info ( nodeType:property )"
        ::= { qpid010SubscriptionEntry 7 }

--
-- qpid010SubscriptionArguments data object
--
qpid010SubscriptionArguments OBJECT-TYPE
        SYNTAX      Map
        MAX-ACCESS  read-write
        STATUS      current
        DESCRIPTION "Subscription arguments
                     Additional info ( nodeType:property )"
        ::= { qpid010SubscriptionEntry 8 }

--
-- qpid010SubscriptionDelivered data object
--
qpid010SubscriptionDelivered OBJECT-TYPE
        SYNTAX      Counter64
        UNITS       "message"
        MAX-ACCESS  read-only
        STATUS      current
        DESCRIPTION "Messages delivered
                     Additional info ( nodeType:statistic )"
        ::= { qpid010SubscriptionEntry 9 }

--
-- subscriptionInternalIndex index column
--
qpid010SubscriptionInternalIndex OBJECT-TYPE
        SYNTAX      Unsigned32
        MAX-ACCESS  not-accessible
        STATUS      current
        DESCRIPTION "Internal index for subscription table"
        ::= { qpid010SubscriptionEntry 10 }
-- ______________________________________________________________
-- Connection class table definition
-- ______________________________________________________________
qpid010ConnectionTable OBJECT-TYPE
        SYNTAX      SEQUENCE OF Qpid010ConnectionEntry
        MAX-ACCESS  not-accessible
        STATUS      current
        DESCRIPTION "table of connections"
        ::= { qpid010Connections 1 }
--
-- connectionEntry row definition
--
qpid010ConnectionEntry OBJECT-TYPE
        SYNTAX      Qpid010ConnectionEntry
        MAX-ACCESS  not-accessible
        STATUS      current
        DESCRIPTION "A row in the connection table"
        INDEX { qpid010ConnectionInternalIndex }
        ::= { qpid010ConnectionTable 1 }

Qpid010ConnectionEntry ::= SEQUENCE {
    qpid010ConnectionVhostRef            ObjId,
    qpid010ConnectionAddress             Sstr,
    qpid010ConnectionIncoming            TruthValue,
    qpid010ConnectionSystemConnection    TruthValue,
    qpid010ConnectionUserProxyAuth       TruthValue,
    qpid010ConnectionFederationLink      TruthValue,
    qpid010ConnectionAuthIdentity        Sstr,
    qpid010ConnectionRemoteProcessName   Lstr,
    qpid010ConnectionRemotePid           Unsigned32,
    qpid010ConnectionRemoteParentPid     Unsigned32,
    qpid010ConnectionShadow              TruthValue,
    qpid010ConnectionSaslMechanism       Sstr,
    qpid010ConnectionSaslSsf             Uint16,
    qpid010ConnectionClosing             TruthValue,
    qpid010ConnectionFramesFromClient    Counter64,
    qpid010ConnectionFramesToClient      Counter64,
    qpid010ConnectionBytesFromClient     Counter64,
    qpid010ConnectionBytesToClient       Counter64,
    qpid010ConnectionMsgsFromClient      Counter64,
    qpid010ConnectionMsgsToClient        Counter64,
    qpid010ConnectionInternalIndex           Unsigned32
}

--
-- qpid010ConnectionVhostRef data object
--
qpid010ConnectionVhostRef OBJECT-TYPE
        SYNTAX      ObjId
        MAX-ACCESS  read-write
        STATUS      current
        DESCRIPTION "Connection vhostRef
                     Additional info ( nodeType:property, references:Vhost, index:y, parentRef:y )"
        ::= { qpid010ConnectionEntry 1 }

--
-- qpid010ConnectionAddress data object
--
qpid010ConnectionAddress OBJECT-TYPE
        SYNTAX      Sstr
        MAX-ACCESS  read-write
        STATUS      current
        DESCRIPTION "Connection address
                     Additional info ( nodeType:property, index:y )"
        ::= { qpid010ConnectionEntry 2 }

--
-- qpid010ConnectionIncoming data object
--
qpid010ConnectionIncoming OBJECT-TYPE
        SYNTAX      TruthValue
        MAX-ACCESS  read-write
        STATUS      current
        DESCRIPTION "Connection incoming
                     Additional info ( nodeType:property )"
        ::= { qpid010ConnectionEntry 3 }

--
-- qpid010ConnectionSystemConnection data object
--
qpid010ConnectionSystemConnection OBJECT-TYPE
        SYNTAX      TruthValue
        MAX-ACCESS  read-write
        STATUS      current
        DESCRIPTION "Infrastructure/ Inter-system connection (Cluster, Federation, ...)
                     Additional info ( nodeType:property )"
        ::= { qpid010ConnectionEntry 4 }

--
-- qpid010ConnectionUserProxyAuth data object
--
qpid010ConnectionUserProxyAuth OBJECT-TYPE
        SYNTAX      TruthValue
        MAX-ACCESS  read-only
        STATUS      current
        DESCRIPTION "Authorization to proxy for users not on broker
                     Additional info ( nodeType:property )"
        ::= { qpid010ConnectionEntry 5 }

--
-- qpid010ConnectionFederationLink data object
--
qpid010ConnectionFederationLink OBJECT-TYPE
        SYNTAX      TruthValue
        MAX-ACCESS  read-only
        STATUS      current
        DESCRIPTION "Is this a federation link
                     Additional info ( nodeType:property )"
        ::= { qpid010ConnectionEntry 6 }

--
-- qpid010ConnectionAuthIdentity data object
--
qpid010ConnectionAuthIdentity OBJECT-TYPE
        SYNTAX      Sstr
        MAX-ACCESS  read-only
        STATUS      current
        DESCRIPTION "authId of connection if authentication enabled
                     Additional info ( nodeType:property )"
        ::= { qpid010ConnectionEntry 7 }

--
-- qpid010ConnectionRemoteProcessName data object
--
qpid010ConnectionRemoteProcessName OBJECT-TYPE
        SYNTAX      Lstr
        MAX-ACCESS  read-only
        STATUS      current
        DESCRIPTION "Name of executable running as remote client
                     Additional info ( nodeType:property, optional:y )"
        ::= { qpid010ConnectionEntry 8 }

--
-- qpid010ConnectionRemotePid data object
--
qpid010ConnectionRemotePid OBJECT-TYPE
        SYNTAX      Unsigned32
        MAX-ACCESS  read-only
        STATUS      current
        DESCRIPTION "Process ID of remote client
                     Additional info ( nodeType:property, optional:y )"
        ::= { qpid010ConnectionEntry 9 }

--
-- qpid010ConnectionRemoteParentPid data object
--
qpid010ConnectionRemoteParentPid OBJECT-TYPE
        SYNTAX      Unsigned32
        MAX-ACCESS  read-only
        STATUS      current
        DESCRIPTION "Parent Process ID of remote client
                     Additional info ( nodeType:property, optional:y )"
        ::= { qpid010ConnectionEntry 10 }

--
-- qpid010ConnectionShadow data object
--
qpid010ConnectionShadow OBJECT-TYPE
        SYNTAX      TruthValue
        MAX-ACCESS  read-only
        STATUS      current
        DESCRIPTION "True for shadow connections
                     Additional info ( nodeType:property )"
        ::= { qpid010ConnectionEntry 11 }

--
-- qpid010ConnectionSaslMechanism data object
--
qpid010ConnectionSaslMechanism OBJECT-TYPE
        SYNTAX      Sstr
        MAX-ACCESS  read-only
        STATUS      current
        DESCRIPTION "SASL mechanism
                     Additional info ( nodeType:property )"
        ::= { qpid010ConnectionEntry 12 }

--
-- qpid010ConnectionSaslSsf data object
--
qpid010ConnectionSaslSsf OBJECT-TYPE
        SYNTAX      Uint16
        MAX-ACCESS  read-only
        STATUS      current
        DESCRIPTION "SASL security strength factor
                     Additional info ( nodeType:property )"
        ::= { qpid010ConnectionEntry 13 }

--
-- qpid010ConnectionClosing data object
--
qpid010ConnectionClosing OBJECT-TYPE
        SYNTAX      TruthValue
        MAX-ACCESS  read-only
        STATUS      current
        DESCRIPTION "This client is closing by management request
                     Additional info ( nodeType:statistic )"
        ::= { qpid010ConnectionEntry 14 }

--
-- qpid010ConnectionFramesFromClient data object
--
qpid010ConnectionFramesFromClient OBJECT-TYPE
        SYNTAX      Counter64
        MAX-ACCESS  read-only
        STATUS      current
        DESCRIPTION "Connection framesFromClient
                     Additional info ( nodeType:statistic )"
        ::= { qpid010ConnectionEntry 15 }

--
-- qpid010ConnectionFramesToClient data object
--
qpid010ConnectionFramesToClient OBJECT-TYPE
        SYNTAX      Counter64
        MAX-ACCESS  read-only
        STATUS      current
        DESCRIPTION "Connection framesToClient
                     Additional info ( nodeType:statistic )"
        ::= { qpid010ConnectionEntry 16 }

--
-- qpid010ConnectionBytesFromClient data object
--
qpid010ConnectionBytesFromClient OBJECT-TYPE
        SYNTAX      Counter64
        MAX-ACCESS  read-only
        STATUS      current
        DESCRIPTION "Connection bytesFromClient
                     Additional info ( nodeType:statistic )"
        ::= { qpid010ConnectionEntry 17 }

--
-- qpid010ConnectionBytesToClient data object
--
qpid010ConnectionBytesToClient OBJECT-TYPE
        SYNTAX      Counter64
        MAX-ACCESS  read-only
        STATUS      current
        DESCRIPTION "Connection bytesToClient
                     Additional info ( nodeType:statistic )"
        ::= { qpid010ConnectionEntry 18 }

--
-- qpid010ConnectionMsgsFromClient data object
--
qpid010ConnectionMsgsFromClient OBJECT-TYPE
        SYNTAX      Counter64
        MAX-ACCESS  read-only
        STATUS      current
        DESCRIPTION "Connection msgsFromClient
                     Additional info ( nodeType:statistic )"
        ::= { qpid010ConnectionEntry 19 }

--
-- qpid010ConnectionMsgsToClient data object
--
qpid010ConnectionMsgsToClient OBJECT-TYPE
        SYNTAX      Counter64
        MAX-ACCESS  read-only
        STATUS      current
        DESCRIPTION "Connection msgsToClient
                     Additional info ( nodeType:statistic )"
        ::= { qpid010ConnectionEntry 20 }

--
-- connectionInternalIndex index column
--
qpid010ConnectionInternalIndex OBJECT-TYPE
        SYNTAX      Unsigned32
        MAX-ACCESS  not-accessible
        STATUS      current
        DESCRIPTION "Internal index for connection table"
        ::= { qpid010ConnectionEntry 21 }
-- ______________________________________________________________
-- Link class table definition
-- ______________________________________________________________
qpid010LinkTable OBJECT-TYPE
        SYNTAX      SEQUENCE OF Qpid010LinkEntry
        MAX-ACCESS  not-accessible
        STATUS      current
        DESCRIPTION "table of links"
        ::= { qpid010Links 1 }
--
-- linkEntry row definition
--
qpid010LinkEntry OBJECT-TYPE
        SYNTAX      Qpid010LinkEntry
        MAX-ACCESS  not-accessible
        STATUS      current
        DESCRIPTION "A row in the link table"
        INDEX { qpid010LinkInternalIndex }
        ::= { qpid010LinkTable 1 }

Qpid010LinkEntry ::= SEQUENCE {
    qpid010LinkVhostRef                  ObjId,
    qpid010LinkName                      Sstr,
    qpid010LinkHost                      Sstr,
    qpid010LinkPort                      Uint16,
    qpid010LinkTransport                 Sstr,
    qpid010LinkDurable                   TruthValue,
    qpid010LinkConnectionRef             ObjId,
    qpid010LinkState                     Sstr,
    qpid010LinkLastError                 Lstr,
    qpid010LinkInternalIndex           Unsigned32
}

--
-- qpid010LinkVhostRef data object
--
qpid010LinkVhostRef OBJECT-TYPE
        SYNTAX      ObjId
        MAX-ACCESS  read-write
        STATUS      current
        DESCRIPTION "Link vhostRef
                     Additional info ( nodeType:property, references:Vhost, index:y, parentRef:y )"
        ::= { qpid010LinkEntry 1 }

--
-- qpid010LinkName data object
--
qpid010LinkName OBJECT-TYPE
        SYNTAX      Sstr
        MAX-ACCESS  read-write
        STATUS      current
        DESCRIPTION "Link name
                     Additional info ( nodeType:property, index:y )"
        ::= { qpid010LinkEntry 2 }

--
-- qpid010LinkHost data object
--
qpid010LinkHost OBJECT-TYPE
        SYNTAX      Sstr
        MAX-ACCESS  read-only
        STATUS      current
        DESCRIPTION "Link host
                     Additional info ( nodeType:property )"
        ::= { qpid010LinkEntry 3 }

--
-- qpid010LinkPort data object
--
qpid010LinkPort OBJECT-TYPE
        SYNTAX      Uint16
        MAX-ACCESS  read-only
        STATUS      current
        DESCRIPTION "Link port
                     Additional info ( nodeType:property )"
        ::= { qpid010LinkEntry 4 }

--
-- qpid010LinkTransport data object
--
qpid010LinkTransport OBJECT-TYPE
        SYNTAX      Sstr
        MAX-ACCESS  read-only
        STATUS      current
        DESCRIPTION "Link transport
                     Additional info ( nodeType:property )"
        ::= { qpid010LinkEntry 5 }

--
-- qpid010LinkDurable data object
--
qpid010LinkDurable OBJECT-TYPE
        SYNTAX      TruthValue
        MAX-ACCESS  read-write
        STATUS      current
        DESCRIPTION "Link durable
                     Additional info ( nodeType:property )"
        ::= { qpid010LinkEntry 6 }

--
-- qpid010LinkConnectionRef data object
--
qpid010LinkConnectionRef OBJECT-TYPE
        SYNTAX      ObjId
        MAX-ACCESS  read-only
        STATUS      current
        DESCRIPTION "Link connectionRef
                     Additional info ( nodeType:property, references:Connection )"
        ::= { qpid010LinkEntry 7 }

--
-- qpid010LinkState data object
--
qpid010LinkState OBJECT-TYPE
        SYNTAX      Sstr
        MAX-ACCESS  read-only
        STATUS      current
        DESCRIPTION "Operational state of the link
                     Additional info ( nodeType:statistic )"
        ::= { qpid010LinkEntry 8 }

--
-- qpid010LinkLastError data object
--
qpid010LinkLastError OBJECT-TYPE
        SYNTAX      Lstr
        MAX-ACCESS  read-only
        STATUS      current
        DESCRIPTION "Reason link is not operational
                     Additional info ( nodeType:statistic )"
        ::= { qpid010LinkEntry 9 }

--
-- linkInternalIndex index column
--
qpid010LinkInternalIndex OBJECT-TYPE
        SYNTAX      Unsigned32
        MAX-ACCESS  not-accessible
        STATUS      current
        DESCRIPTION "Internal index for link table"
        ::= { qpid010LinkEntry 10 }
-- ______________________________________________________________
-- Bridge class table definition
-- ______________________________________________________________
qpid010BridgeTable OBJECT-TYPE
        SYNTAX      SEQUENCE OF Qpid010BridgeEntry
        MAX-ACCESS  not-accessible
        STATUS      current
        DESCRIPTION "table of bridges"
        ::= { qpid010Bridges 1 }
--
-- bridgeEntry row definition
--
qpid010BridgeEntry OBJECT-TYPE
        SYNTAX      Qpid010BridgeEntry
        MAX-ACCESS  not-accessible
        STATUS      current
        DESCRIPTION "A row in the bridge table"
        INDEX { qpid010BridgeInternalIndex }
        ::= { qpid010BridgeTable 1 }

Qpid010BridgeEntry ::= SEQUENCE {
    qpid010BridgeLinkRef                 ObjId,
    qpid010BridgeName                    Sstr,
    qpid010BridgeChannelId               Uint16,
    qpid010BridgeDurable                 TruthValue,
    qpid010BridgeSrc                     Sstr,
    qpid010BridgeDest                    Sstr,
    qpid010BridgeKey                     Lstr,
    qpid010BridgeSrcIsQueue              TruthValue,
    qpid010BridgeSrcIsLocal              TruthValue,
    qpid010BridgeTag                     Sstr,
    qpid010BridgeExcludes                Sstr,
    qpid010BridgeDynamic                 TruthValue,
    qpid010BridgeSync                    Uint16,
    qpid010BridgeInternalIndex           Unsigned32
}

--
-- qpid010BridgeLinkRef data object
--
qpid010BridgeLinkRef OBJECT-TYPE
        SYNTAX      ObjId
        MAX-ACCESS  read-write
        STATUS      current
        DESCRIPTION "Bridge linkRef
                     Additional info ( nodeType:property, references:Link, index:y, parentRef:y )"
        ::= { qpid010BridgeEntry 1 }

--
-- qpid010BridgeName data object
--
qpid010BridgeName OBJECT-TYPE
        SYNTAX      Sstr
        MAX-ACCESS  read-write
        STATUS      current
        DESCRIPTION "Bridge name
                     Additional info ( nodeType:property, index:y )"
        ::= { qpid010BridgeEntry 2 }

--
-- qpid010BridgeChannelId data object
--
qpid010BridgeChannelId OBJECT-TYPE
        SYNTAX      Uint16
        MAX-ACCESS  read-only
        STATUS      current
        DESCRIPTION "Bridge channelId
                     Additional info ( nodeType:property )"
        ::= { qpid010BridgeEntry 3 }

--
-- qpid010BridgeDurable data object
--
qpid010BridgeDurable OBJECT-TYPE
        SYNTAX      TruthValue
        MAX-ACCESS  read-write
        STATUS      current
        DESCRIPTION "Bridge durable
                     Additional info ( nodeType:property )"
        ::= { qpid010BridgeEntry 4 }

--
-- qpid010BridgeSrc data object
--
qpid010BridgeSrc OBJECT-TYPE
        SYNTAX      Sstr
        MAX-ACCESS  read-write
        STATUS      current
        DESCRIPTION "Bridge src
                     Additional info ( nodeType:property )"
        ::= { qpid010BridgeEntry 5 }

--
-- qpid010BridgeDest data object
--
qpid010BridgeDest OBJECT-TYPE
        SYNTAX      Sstr
        MAX-ACCESS  read-write
        STATUS      current
        DESCRIPTION "Bridge dest
                     Additional info ( nodeType:property )"
        ::= { qpid010BridgeEntry 6 }

--
-- qpid010BridgeKey data object
--
qpid010BridgeKey OBJECT-TYPE
        SYNTAX      Lstr
        MAX-ACCESS  read-write
        STATUS      current
        DESCRIPTION "Bridge key
                     Additional info ( nodeType:property )"
        ::= { qpid010BridgeEntry 7 }

--
-- qpid010BridgeSrcIsQueue data object
--
qpid010BridgeSrcIsQueue OBJECT-TYPE
        SYNTAX      TruthValue
        MAX-ACCESS  read-write
        STATUS      current
        DESCRIPTION "Bridge srcIsQueue
                     Additional info ( nodeType:property )"
        ::= { qpid010BridgeEntry 8 }

--
-- qpid010BridgeSrcIsLocal data object
--
qpid010BridgeSrcIsLocal OBJECT-TYPE
        SYNTAX      TruthValue
        MAX-ACCESS  read-write
        STATUS      current
        DESCRIPTION "Bridge srcIsLocal
                     Additional info ( nodeType:property )"
        ::= { qpid010BridgeEntry 9 }

--
-- qpid010BridgeTag data object
--
qpid010BridgeTag OBJECT-TYPE
        SYNTAX      Sstr
        MAX-ACCESS  read-write
        STATUS      current
        DESCRIPTION "Bridge tag
                     Additional info ( nodeType:property )"
        ::= { qpid010BridgeEntry 10 }

--
-- qpid010BridgeExcludes data object
--
qpid010BridgeExcludes OBJECT-TYPE
        SYNTAX      Sstr
        MAX-ACCESS  read-write
        STATUS      current
        DESCRIPTION "Bridge excludes
                     Additional info ( nodeType:property )"
        ::= { qpid010BridgeEntry 11 }

--
-- qpid010BridgeDynamic data object
--
qpid010BridgeDynamic OBJECT-TYPE
        SYNTAX      TruthValue
        MAX-ACCESS  read-write
        STATUS      current
        DESCRIPTION "Bridge dynamic
                     Additional info ( nodeType:property )"
        ::= { qpid010BridgeEntry 12 }

--
-- qpid010BridgeSync data object
--
qpid010BridgeSync OBJECT-TYPE
        SYNTAX      Uint16
        MAX-ACCESS  read-write
        STATUS      current
        DESCRIPTION "Bridge sync
                     Additional info ( nodeType:property )"
        ::= { qpid010BridgeEntry 13 }

--
-- bridgeInternalIndex index column
--
qpid010BridgeInternalIndex OBJECT-TYPE
        SYNTAX      Unsigned32
        MAX-ACCESS  not-accessible
        STATUS      current
        DESCRIPTION "Internal index for bridge table"
        ::= { qpid010BridgeEntry 14 }
-- ______________________________________________________________
-- Session class table definition
-- ______________________________________________________________
qpid010SessionTable OBJECT-TYPE
        SYNTAX      SEQUENCE OF Qpid010SessionEntry
        MAX-ACCESS  not-accessible
        STATUS      current
        DESCRIPTION "table of sessions"
        ::= { qpid010Sessions 1 }
--
-- sessionEntry row definition
--
qpid010SessionEntry OBJECT-TYPE
        SYNTAX      Qpid010SessionEntry
        MAX-ACCESS  not-accessible
        STATUS      current
        DESCRIPTION "A row in the session table"
        INDEX { qpid010SessionInternalIndex }
        ::= { qpid010SessionTable 1 }

Qpid010SessionEntry ::= SEQUENCE {
    qpid010SessionVhostRef               ObjId,
    qpid010SessionName                   Sstr,
    qpid010SessionChannelId              Uint16,
    qpid010SessionConnectionRef          ObjId,
    qpid010SessionDetachedLifespan       Unsigned32,
    qpid010SessionAttached               TruthValue,
    qpid010SessionExpireTime             TimeTicks,
    qpid010SessionMaxClientRate          Unsigned32,
    qpid010SessionUnackedMessages        Uint64,
    qpid010SessionTxnStarts              Counter64,
    qpid010SessionTxnCommits             Counter64,
    qpid010SessionTxnRejects             Counter64,
    qpid010SessionTxnCount               Counter32,
    qpid010SessionClientCredit           Counter32,
    qpid010SessionInternalIndex           Unsigned32
}

--
-- qpid010SessionVhostRef data object
--
qpid010SessionVhostRef OBJECT-TYPE
        SYNTAX      ObjId
        MAX-ACCESS  read-write
        STATUS      current
        DESCRIPTION "Session vhostRef
                     Additional info ( nodeType:property, references:Vhost, index:y, parentRef:y )"
        ::= { qpid010SessionEntry 1 }

--
-- qpid010SessionName data object
--
qpid010SessionName OBJECT-TYPE
        SYNTAX      Sstr
        MAX-ACCESS  read-write
        STATUS      current
        DESCRIPTION "Session name
                     Additional info ( nodeType:property, index:y )"
        ::= { qpid010SessionEntry 2 }

--
-- qpid010SessionChannelId data object
--
qpid010SessionChannelId OBJECT-TYPE
        SYNTAX      Uint16
        MAX-ACCESS  read-only
        STATUS      current
        DESCRIPTION "Session channelId
                     Additional info ( nodeType:property )"
        ::= { qpid010SessionEntry 3 }

--
-- qpid010SessionConnectionRef data object
--
qpid010SessionConnectionRef OBJECT-TYPE
        SYNTAX      ObjId
        MAX-ACCESS  read-only
        STATUS      current
        DESCRIPTION "Session connectionRef
                     Additional info ( nodeType:property, references:Connection )"
        ::= { qpid010SessionEntry 4 }

--
-- qpid010SessionDetachedLifespan data object
--
qpid010SessionDetachedLifespan OBJECT-TYPE
        SYNTAX      Unsigned32
        UNITS       "second"
        MAX-ACCESS  read-only
        STATUS      current
        DESCRIPTION "Session detachedLifespan
                     Additional info ( nodeType:property )"
        ::= { qpid010SessionEntry 5 }

--
-- qpid010SessionAttached data object
--
qpid010SessionAttached OBJECT-TYPE
        SYNTAX      TruthValue
        MAX-ACCESS  read-only
        STATUS      current
        DESCRIPTION "Session attached
                     Additional info ( nodeType:property )"
        ::= { qpid010SessionEntry 6 }

--
-- qpid010SessionExpireTime data object
--
qpid010SessionExpireTime OBJECT-TYPE
        SYNTAX      TimeTicks
        MAX-ACCESS  read-only
        STATUS      current
        DESCRIPTION "Session expireTime
                     Additional info ( nodeType:property, optional:y )"
        ::= { qpid010SessionEntry 7 }

--
-- qpid010SessionMaxClientRate data object
--
qpid010SessionMaxClientRate OBJECT-TYPE
        SYNTAX      Unsigned32
        UNITS       "msgs/sec"
        MAX-ACCESS  read-only
        STATUS      current
        DESCRIPTION "Session maxClientRate
                     Additional info ( nodeType:property, optional:y )"
        ::= { qpid010SessionEntry 8 }

--
-- qpid010SessionUnackedMessages data object
--
qpid010SessionUnackedMessages OBJECT-TYPE
        SYNTAX      Uint64
        UNITS       "message"
        MAX-ACCESS  read-only
        STATUS      current
        DESCRIPTION "Unacknowledged messages in the session
                     Additional info ( nodeType:statistic )"
        ::= { qpid010SessionEntry 9 }

--
-- qpid010SessionTxnStarts data object
--
qpid010SessionTxnStarts OBJECT-TYPE
        SYNTAX      Counter64
        UNITS       "transaction"
        MAX-ACCESS  read-only
        STATUS      current
        DESCRIPTION "Total transactions started 
                     Additional info ( nodeType:statistic )"
        ::= { qpid010SessionEntry 10 }

--
-- qpid010SessionTxnCommits data object
--
qpid010SessionTxnCommits OBJECT-TYPE
        SYNTAX      Counter64
        UNITS       "transaction"
        MAX-ACCESS  read-only
        STATUS      current
        DESCRIPTION "Total transactions committed
                     Additional info ( nodeType:statistic )"
        ::= { qpid010SessionEntry 11 }

--
-- qpid010SessionTxnRejects data object
--
qpid010SessionTxnRejects OBJECT-TYPE
        SYNTAX      Counter64
        UNITS       "transaction"
        MAX-ACCESS  read-only
        STATUS      current
        DESCRIPTION "Total transactions rejected
                     Additional info ( nodeType:statistic )"
        ::= { qpid010SessionEntry 12 }

--
-- qpid010SessionTxnCount data object
--
qpid010SessionTxnCount OBJECT-TYPE
        SYNTAX      Counter32
        UNITS       "transaction"
        MAX-ACCESS  read-only
        STATUS      current
        DESCRIPTION "Current pending transactions
                     Additional info ( nodeType:statistic )"
        ::= { qpid010SessionEntry 13 }

--
-- qpid010SessionClientCredit data object
--
qpid010SessionClientCredit OBJECT-TYPE
        SYNTAX      Counter32
        UNITS       "message"
        MAX-ACCESS  read-only
        STATUS      current
        DESCRIPTION "Client message credit
                     Additional info ( nodeType:statistic )"
        ::= { qpid010SessionEntry 14 }

--
-- sessionInternalIndex index column
--
qpid010SessionInternalIndex OBJECT-TYPE
        SYNTAX      Unsigned32
        MAX-ACCESS  not-accessible
        STATUS      current
        DESCRIPTION "Internal index for session table"
        ::= { qpid010SessionEntry 15 }
-- ______________________________________________________________
-- ManagementSetupState class properties and statistics
-- ______________________________________________________________

--
-- The ManagementSetupStateObjectNum data object
--
qpid010ManagementSetupStateObjectNum OBJECT-TYPE
        SYNTAX      Uint64
        MAX-ACCESS  read-only
        STATUS      current
        DESCRIPTION "ManagementSetupState objectNum
                     Additional info ( nodeType:property )"
        ::= { qpid010ManagementSetupState 1 }

--
-- The ManagementSetupStateBootSequence data object
--
qpid010ManagementSetupStateBootSequence OBJECT-TYPE
        SYNTAX      Uint16
        MAX-ACCESS  read-only
        STATUS      current
        DESCRIPTION "ManagementSetupState bootSequence
                     Additional info ( nodeType:property )"
        ::= { qpid010ManagementSetupState 2 }


-- ______________________________________________________________
-- Acl plugin class properties and statistics
-- ______________________________________________________________

--
-- The AclBrokerRef data object
--
qpid010AclBrokerRef OBJECT-TYPE
        SYNTAX      ObjId
        MAX-ACCESS  read-only
        STATUS      current
        DESCRIPTION "Acl brokerRef
                     Additional info ( nodeType:property, references:org.apache.qpid.broker:Broker, index:y, parentRef:y )"
        ::= { qpid010Acl 1 }

--
-- The AclPolicyFile data object
--
qpid010AclPolicyFile OBJECT-TYPE
        SYNTAX      Lstr
        MAX-ACCESS  read-only
        STATUS      current
        DESCRIPTION "Name of the policy file
                     Additional info ( nodeType:property )"
        ::= { qpid010Acl 2 }

--
-- The AclEnforcingAcl data object
--
qpid010AclEnforcingAcl OBJECT-TYPE
        SYNTAX      TruthValue
        MAX-ACCESS  read-only
        STATUS      current
        DESCRIPTION "Currently Enforcing ACL
                     Additional info ( nodeType:property )"
        ::= { qpid010Acl 3 }

--
-- The AclTransferAcl data object
--
qpid010AclTransferAcl OBJECT-TYPE
        SYNTAX      TruthValue
        MAX-ACCESS  read-only
        STATUS      current
        DESCRIPTION "Any transfer ACL rules in force
                     Additional info ( nodeType:property )"
        ::= { qpid010Acl 4 }

--
-- The AclLastAclLoad data object
--
qpid010AclLastAclLoad OBJECT-TYPE
        SYNTAX      TimeTicks
        MAX-ACCESS  read-only
        STATUS      current
        DESCRIPTION "Timestamp of last successful load of ACL
                     Additional info ( nodeType:property )"
        ::= { qpid010Acl 5 }

--
-- The AclMaxConnections data object
--
qpid010AclMaxConnections OBJECT-TYPE
        SYNTAX      Uint16
        MAX-ACCESS  read-only
        STATUS      current
        DESCRIPTION "Maximum allowed connections
                     Additional info ( nodeType:property )"
        ::= { qpid010Acl 6 }

--
-- The AclMaxConnectionsPerIp data object
--
qpid010AclMaxConnectionsPerIp OBJECT-TYPE
        SYNTAX      Uint16
        MAX-ACCESS  read-only
        STATUS      current
        DESCRIPTION "Maximum allowed connections
                     Additional info ( nodeType:property )"
        ::= { qpid010Acl 7 }

--
-- The AclMaxConnectionsPerUser data object
--
qpid010AclMaxConnectionsPerUser OBJECT-TYPE
        SYNTAX      Uint16
        MAX-ACCESS  read-only
        STATUS      current
        DESCRIPTION "Maximum allowed connections
                     Additional info ( nodeType:property )"
        ::= { qpid010Acl 8 }

--
-- The AclAclDenyCount data object
--
qpid010AclAclDenyCount OBJECT-TYPE
        SYNTAX      Counter64
        UNITS       "request"
        MAX-ACCESS  read-only
        STATUS      current
        DESCRIPTION "Number of ACL requests denied
                     Additional info ( nodeType:statistic )"
        ::= { qpid010Acl 9 }

--
-- The AclConnectionDenyCount data object
--
qpid010AclConnectionDenyCount OBJECT-TYPE
        SYNTAX      Counter64
        UNITS       "connection"
        MAX-ACCESS  read-only
        STATUS      current
        DESCRIPTION "Number of connections denied
                     Additional info ( nodeType:statistic )"
        ::= { qpid010Acl 10 }

-- ______________________________________________________________
-- Cluster plugin class properties and statistics
-- ______________________________________________________________

--
-- The ClusterBrokerRef data object
--
qpid010ClusterBrokerRef OBJECT-TYPE
        SYNTAX      ObjId
        MAX-ACCESS  read-write
        STATUS      current
        DESCRIPTION "Cluster brokerRef
                     Additional info ( nodeType:property, references:Broker, index:y, parentRef:y )"
        ::= { qpid010Cluster 1 }

--
-- The ClusterClusterName data object
--
qpid010ClusterClusterName OBJECT-TYPE
        SYNTAX      Sstr
        MAX-ACCESS  read-write
        STATUS      current
        DESCRIPTION "Name of cluster this server is a member of
                     Additional info ( nodeType:property )"
        ::= { qpid010Cluster 2 }

--
-- The ClusterClusterID data object
--
qpid010ClusterClusterID OBJECT-TYPE
        SYNTAX      Sstr
        MAX-ACCESS  read-only
        STATUS      current
        DESCRIPTION "Globally unique ID (UUID) for this cluster instance
                     Additional info ( nodeType:property )"
        ::= { qpid010Cluster 3 }

--
-- The ClusterMemberID data object
--
qpid010ClusterMemberID OBJECT-TYPE
        SYNTAX      Sstr
        MAX-ACCESS  read-only
        STATUS      current
        DESCRIPTION "ID of this member of the cluster
                     Additional info ( nodeType:property )"
        ::= { qpid010Cluster 4 }

--
-- The ClusterPublishedURL data object
--
qpid010ClusterPublishedURL OBJECT-TYPE
        SYNTAX      Sstr
        MAX-ACCESS  read-write
        STATUS      current
        DESCRIPTION "URL this node advertizes itself as
                     Additional info ( nodeType:property )"
        ::= { qpid010Cluster 5 }

--
-- The ClusterClusterSize data object
--
qpid010ClusterClusterSize OBJECT-TYPE
        SYNTAX      Uint16
        MAX-ACCESS  read-only
        STATUS      current
        DESCRIPTION "Number of brokers currently in the cluster
                     Additional info ( nodeType:property )"
        ::= { qpid010Cluster 6 }

--
-- The ClusterStatus data object
--
qpid010ClusterStatus OBJECT-TYPE
        SYNTAX      Sstr
        MAX-ACCESS  read-only
        STATUS      current
        DESCRIPTION "Cluster node status (STALLED,ACTIVE,JOINING)
                     Additional info ( nodeType:property )"
        ::= { qpid010Cluster 7 }

--
-- The ClusterMembers data object
--
qpid010ClusterMembers OBJECT-TYPE
        SYNTAX      Lstr
        MAX-ACCESS  read-only
        STATUS      current
        DESCRIPTION "List of member URLs delimited by ';'
                     Additional info ( nodeType:property )"
        ::= { qpid010Cluster 8 }

--
-- The ClusterMemberIDs data object
--
qpid010ClusterMemberIDs OBJECT-TYPE
        SYNTAX      Lstr
        MAX-ACCESS  read-only
        STATUS      current
        DESCRIPTION "List of member IDs delimited by ';'
                     Additional info ( nodeType:property )"
        ::= { qpid010Cluster 9 }

-- ______________________________________________________________
-- HaBroker plugin class properties and statistics
-- ______________________________________________________________

--
-- The HaBrokerName data object
--
qpid010HaBrokerName OBJECT-TYPE
        SYNTAX      Sstr
        MAX-ACCESS  read-write
        STATUS      current
        DESCRIPTION "Primary Key
                     Additional info ( nodeType:property, index:y )"
        ::= { qpid010HaBroker 1 }

--
-- The HaBrokerStatus data object
--
qpid010HaBrokerStatus OBJECT-TYPE
        SYNTAX      Sstr
        MAX-ACCESS  read-only
        STATUS      current
        DESCRIPTION "HA status: primary or backup
                     Additional info ( nodeType:property )"
        ::= { qpid010HaBroker 2 }

--
-- The HaBrokerBrokersUrl data object
--
qpid010HaBrokerBrokersUrl OBJECT-TYPE
        SYNTAX      Sstr
        MAX-ACCESS  read-only
        STATUS      current
        DESCRIPTION "URL with address of each broker in the cluster.
                     Additional info ( nodeType:property )"
        ::= { qpid010HaBroker 3 }

--
-- The HaBrokerPublicUrl data object
--
qpid010HaBrokerPublicUrl OBJECT-TYPE
        SYNTAX      Sstr
        MAX-ACCESS  read-only
        STATUS      current
        DESCRIPTION "URL advertized to clients to connect to the cluster.
                     Additional info ( nodeType:property )"
        ::= { qpid010HaBroker 4 }

--
-- The HaBrokerReplicateDefault data object
--
qpid010HaBrokerReplicateDefault OBJECT-TYPE
        SYNTAX      Sstr
        MAX-ACCESS  read-only
        STATUS      current
        DESCRIPTION "Replication for queues/exchanges with no qpid.replicate argument
                     Additional info ( nodeType:property )"
        ::= { qpid010HaBroker 5 }

--
-- The HaBrokerMembers data object
--
qpid010HaBrokerMembers OBJECT-TYPE
        SYNTAX      Sstr
        MAX-ACCESS  read-only
        STATUS      current
        DESCRIPTION "List of brokers in the cluster
                     Additional info ( nodeType:property )"
        ::= { qpid010HaBroker 6 }

--
-- The HaBrokerSystemId data object
--
qpid010HaBrokerSystemId OBJECT-TYPE
        SYNTAX      Uuid
        MAX-ACCESS  read-only
        STATUS      current
        DESCRIPTION "Identifies the system.
                     Additional info ( nodeType:property )"
        ::= { qpid010HaBroker 7 }



--
-- Notification Objects
-- These are the object/parameters that are sent in notification
-- events (when the agent sends a "trap" message to the manager on port 162)
-- ______________________________________________________________
qpid010EvtList OBJECT-IDENTITY
        STATUS      current
        DESCRIPTION "Placeholder needed for SMIv1 managers. Node number must be 0"
        ::= {qpid010Events 0 }

qpid010EvtArgList OBJECT-IDENTITY
        STATUS      current
        DESCRIPTION "Top level node for all the event arguments"
        ::= { qpid010Events 1 }
--
-- Objects that are passed with events
--
qpid010EvtAltEx OBJECT-TYPE
        SYNTAX      Sstr
        MAX-ACCESS  read-only
        STATUS      current
        DESCRIPTION "Name of the alternate exchange"
        ::= { qpid010EvtArgList 1 }

qpid010EvtArgs OBJECT-TYPE
        SYNTAX      Map
        MAX-ACCESS  read-only
        STATUS      current
        DESCRIPTION "Supplemental arguments or parameters supplied"
        ::= { qpid010EvtArgList 2 }

qpid010EvtAutoDel OBJECT-TYPE
        SYNTAX      TruthValue
        MAX-ACCESS  read-only
        STATUS      current
        DESCRIPTION "Created object is automatically deleted when no longer in use"
        ::= { qpid010EvtArgList 3 }

qpid010EvtDest OBJECT-TYPE
        SYNTAX      Sstr
        MAX-ACCESS  read-only
        STATUS      current
        DESCRIPTION "Destination tag for a subscription"
        ::= { qpid010EvtArgList 4 }

qpid010EvtDisp OBJECT-TYPE
        SYNTAX      Sstr
        MAX-ACCESS  read-only
        STATUS      current
        DESCRIPTION "Disposition of a declaration: 'created' if object was created, 'existing' if object already existed"
        ::= { qpid010EvtArgList 5 }

qpid010EvtDurable OBJECT-TYPE
        SYNTAX      TruthValue
        MAX-ACCESS  read-only
        STATUS      current
        DESCRIPTION "Created object is durable"
        ::= { qpid010EvtArgList 6 }

qpid010EvtExName OBJECT-TYPE
        SYNTAX      Sstr
        MAX-ACCESS  read-only
        STATUS      current
        DESCRIPTION "Name of an exchange"
        ::= { qpid010EvtArgList 7 }

qpid010EvtExType OBJECT-TYPE
        SYNTAX      Sstr
        MAX-ACCESS  read-only
        STATUS      current
        DESCRIPTION "Type of an exchange"
        ::= { qpid010EvtArgList 8 }

qpid010EvtExcl OBJECT-TYPE
        SYNTAX      TruthValue
        MAX-ACCESS  read-only
        STATUS      current
        DESCRIPTION "Created object is exclusive for the use of the owner only"
        ::= { qpid010EvtArgList 9 }

qpid010EvtKey OBJECT-TYPE
        SYNTAX      Lstr
        MAX-ACCESS  read-only
        STATUS      current
        DESCRIPTION "Key text used for routing or binding"
        ::= { qpid010EvtArgList 10 }

qpid010EvtQName OBJECT-TYPE
        SYNTAX      Sstr
        MAX-ACCESS  read-only
        STATUS      current
        DESCRIPTION "Name of a queue"
        ::= { qpid010EvtArgList 11 }

qpid010EvtReason OBJECT-TYPE
        SYNTAX      Lstr
        MAX-ACCESS  read-only
        STATUS      current
        DESCRIPTION "Reason for a failure"
        ::= { qpid010EvtArgList 12 }

qpid010EvtRhost OBJECT-TYPE
        SYNTAX      Sstr
        MAX-ACCESS  read-only
        STATUS      current
        DESCRIPTION "Address (i.e. DNS name, IP address, etc.) of a remotely connected host"
        ::= { qpid010EvtArgList 13 }

qpid010EvtUser OBJECT-TYPE
        SYNTAX      Sstr
        MAX-ACCESS  read-only
        STATUS      current
        DESCRIPTION "Authentication identity"
        ::= { qpid010EvtArgList 14 }

qpid010EvtMsgDepth OBJECT-TYPE
        SYNTAX      Counter64
        MAX-ACCESS  read-only
        STATUS      current
        DESCRIPTION "Current size of queue in messages"
        ::= { qpid010EvtArgList 15 }

qpid010EvtByteDepth OBJECT-TYPE
        SYNTAX      Counter64
        MAX-ACCESS  read-only
        STATUS      current
        DESCRIPTION "Current size of queue in bytes"
        ::= { qpid010EvtArgList 16 }

qpid010EvtAction OBJECT-TYPE
        SYNTAX      Sstr
        MAX-ACCESS  read-only
        STATUS      current
        DESCRIPTION "Description for Action is missing from the schema"
        ::= { qpid010EvtArgList 17 }

qpid010EvtArguments OBJECT-TYPE
        SYNTAX      Map
        MAX-ACCESS  read-only
        STATUS      current
        DESCRIPTION "Description for Arguments is missing from the schema"
        ::= { qpid010EvtArgList 18 }

qpid010EvtObjectName OBJECT-TYPE
        SYNTAX      Sstr
        MAX-ACCESS  read-only
        STATUS      current
        DESCRIPTION "Description for ObjectName is missing from the schema"
        ::= { qpid010EvtArgList 19 }

qpid010EvtObjectType OBJECT-TYPE
        SYNTAX      Sstr
        MAX-ACCESS  read-only
        STATUS      current
        DESCRIPTION "Description for ObjectType is missing from the schema"
        ::= { qpid010EvtArgList 20 }

qpid010EvtUserId OBJECT-TYPE
        SYNTAX      Sstr
        MAX-ACCESS  read-only
        STATUS      current
        DESCRIPTION "Description for UserId is missing from the schema"
        ::= { qpid010EvtArgList 21 }

qpid010EvtClientAddr OBJECT-TYPE
        SYNTAX      Sstr
        MAX-ACCESS  read-only
        STATUS      current
        DESCRIPTION "Description for ClientAddr is missing from the schema"
        ::= { qpid010EvtArgList 22 }

qpid010EvtMembers OBJECT-TYPE
        SYNTAX      Sstr
        MAX-ACCESS  read-only
        STATUS      current
        DESCRIPTION "List of broker information maps"
        ::= { qpid010EvtArgList 23 }

--
-- Notfication events that are raised by the agent
--

qpid010EvtClientConnect NOTIFICATION-TYPE
        OBJECTS {
            qpid010EvtRhost, qpid010EvtUser
            }
        STATUS      current
        DESCRIPTION "inform ClientConnect event"
        ::= { qpid010EvtList 1 }

qpid010EvtClientConnectFail NOTIFICATION-TYPE
        OBJECTS {
            qpid010EvtRhost, qpid010EvtUser, qpid010EvtReason
            }
        STATUS      current
        DESCRIPTION "warn ClientConnectFail event"
        ::= { qpid010EvtList 2 }

qpid010EvtClientDisconnect NOTIFICATION-TYPE
        OBJECTS {
            qpid010EvtRhost, qpid010EvtUser
            }
        STATUS      current
        DESCRIPTION "inform ClientDisconnect event"
        ::= { qpid010EvtList 3 }

qpid010EvtBrokerLinkUp NOTIFICATION-TYPE
        OBJECTS {
            qpid010EvtRhost
            }
        STATUS      current
        DESCRIPTION "inform BrokerLinkUp event"
        ::= { qpid010EvtList 4 }

qpid010EvtBrokerLinkDown NOTIFICATION-TYPE
        OBJECTS {
            qpid010EvtRhost
            }
        STATUS      current
        DESCRIPTION "warn BrokerLinkDown event"
        ::= { qpid010EvtList 5 }

qpid010EvtQueueDeclare NOTIFICATION-TYPE
        OBJECTS {
            qpid010EvtRhost, qpid010EvtUser, qpid010EvtQName, qpid010EvtDurable, qpid010EvtExcl, qpid010EvtAutoDel, qpid010EvtAltEx, qpid010EvtArgs, qpid010EvtDisp
            }
        STATUS      current
        DESCRIPTION "inform QueueDeclare event"
        ::= { qpid010EvtList 6 }

qpid010EvtQueueDelete NOTIFICATION-TYPE
        OBJECTS {
            qpid010EvtRhost, qpid010EvtUser, qpid010EvtQName
            }
        STATUS      current
        DESCRIPTION "inform QueueDelete event"
        ::= { qpid010EvtList 7 }

qpid010EvtExchangeDeclare NOTIFICATION-TYPE
        OBJECTS {
            qpid010EvtRhost, qpid010EvtUser, qpid010EvtExName, qpid010EvtExType, qpid010EvtAltEx, qpid010EvtDurable, qpid010EvtAutoDel, qpid010EvtArgs, qpid010EvtDisp
            }
        STATUS      current
        DESCRIPTION "inform ExchangeDeclare event"
        ::= { qpid010EvtList 8 }

qpid010EvtExchangeDelete NOTIFICATION-TYPE
        OBJECTS {
            qpid010EvtRhost, qpid010EvtUser, qpid010EvtExName
            }
        STATUS      current
        DESCRIPTION "inform ExchangeDelete event"
        ::= { qpid010EvtList 9 }

qpid010EvtBind NOTIFICATION-TYPE
        OBJECTS {
            qpid010EvtRhost, qpid010EvtUser, qpid010EvtExName, qpid010EvtQName, qpid010EvtKey, qpid010EvtArgs
            }
        STATUS      current
        DESCRIPTION "inform Bind event"
        ::= { qpid010EvtList 10 }

qpid010EvtUnbind NOTIFICATION-TYPE
        OBJECTS {
            qpid010EvtRhost, qpid010EvtUser, qpid010EvtExName, qpid010EvtQName, qpid010EvtKey
            }
        STATUS      current
        DESCRIPTION "inform Unbind event"
        ::= { qpid010EvtList 11 }

qpid010EvtSubscribe NOTIFICATION-TYPE
        OBJECTS {
            qpid010EvtRhost, qpid010EvtUser, qpid010EvtQName, qpid010EvtDest, qpid010EvtExcl, qpid010EvtArgs
            }
        STATUS      current
        DESCRIPTION "inform Subscribe event"
        ::= { qpid010EvtList 12 }

qpid010EvtUnsubscribe NOTIFICATION-TYPE
        OBJECTS {
            qpid010EvtRhost, qpid010EvtUser, qpid010EvtDest
            }
        STATUS      current
        DESCRIPTION "inform Unsubscribe event"
        ::= { qpid010EvtList 13 }

qpid010EvtQueueThresholdExceeded NOTIFICATION-TYPE
        OBJECTS {
            qpid010EvtQName, qpid010EvtMsgDepth, qpid010EvtByteDepth
            }
        STATUS      current
        DESCRIPTION "warn QueueThresholdExceeded event"
        ::= { qpid010EvtList 14 }

qpid010EvtAllow NOTIFICATION-TYPE
        OBJECTS {
            qpid010EvtUserId, qpid010EvtAction, qpid010EvtObjectType, qpid010EvtObjectName, qpid010EvtArguments
            }
        STATUS      current
        DESCRIPTION "inform Allow event"
        ::= { qpid010EvtList 15 }

qpid010EvtDeny NOTIFICATION-TYPE
        OBJECTS {
            qpid010EvtUserId, qpid010EvtAction, qpid010EvtObjectType, qpid010EvtObjectName, qpid010EvtArguments
            }
        STATUS      current
        DESCRIPTION "notice Deny event"
        ::= { qpid010EvtList 16 }

qpid010EvtConnectionDeny NOTIFICATION-TYPE
        OBJECTS {
            qpid010EvtUserId, qpid010EvtClientAddr
            }
        STATUS      current
        DESCRIPTION "notice ConnectionDeny event"
        ::= { qpid010EvtList 17 }

qpid010EvtFileLoaded NOTIFICATION-TYPE
        OBJECTS {
            qpid010EvtUserId
            }
        STATUS      current
        DESCRIPTION "inform FileLoaded event"
        ::= { qpid010EvtList 18 }

qpid010EvtFileLoadFailed NOTIFICATION-TYPE
        OBJECTS {
            qpid010EvtUserId, qpid010EvtReason
            }
        STATUS      current
        DESCRIPTION "error FileLoadFailed event"
        ::= { qpid010EvtList 19 }

qpid010EvtMembersUpdate NOTIFICATION-TYPE
        OBJECTS {
            qpid010EvtMembers
            }
        STATUS      current
        DESCRIPTION "inform MembersUpdate event"
        ::= { qpid010EvtList 20 }


--
-- Conformance Objects and Groups
-- This puts the data objects and notification events into
-- groups that can be marked as required or optional
-- ______________________________________________________________
qpid010CnfGroups OBJECT-IDENTITY
        STATUS      current
        DESCRIPTION "Root for all groups"
        ::= { qpid010Conformance 1 }

qpid010CnfGrpRequired OBJECT-GROUP
        OBJECTS {
                qpid010SystemSystemId
                ,qpid010SystemOsName
                ,qpid010SystemNodeName
                ,qpid010SystemRelease
                ,qpid010SystemVersion
                ,qpid010SystemMachine
                ,qpid010MemoryName
                ,qpid010BrokerName
                ,qpid010BrokerSystemRef
                ,qpid010BrokerPort
                ,qpid010BrokerWorkerThreads
                ,qpid010BrokerConnBacklog
                ,qpid010BrokerStagingThreshold
                ,qpid010BrokerMgmtPublish
                ,qpid010BrokerMgmtPubInterval
                ,qpid010BrokerVersion
                ,qpid010BrokerUptime
                ,qpid010BrokerQueueCount
                ,qpid010BrokerMsgTotalEnqueues
                ,qpid010BrokerMsgTotalDequeues
                ,qpid010BrokerByteTotalEnqueues
                ,qpid010BrokerByteTotalDequeues
                ,qpid010BrokerMsgDepth
                ,qpid010BrokerByteDepth
                ,qpid010BrokerMsgPersistEnqueues
                ,qpid010BrokerMsgPersistDequeues
                ,qpid010BrokerBytePersistEnqueues
                ,qpid010BrokerBytePersistDequeues
                ,qpid010BrokerMsgTxnEnqueues
                ,qpid010BrokerMsgTxnDequeues
                ,qpid010BrokerByteTxnEnqueues
                ,qpid010BrokerByteTxnDequeues
                ,qpid010BrokerMsgFtdEnqueues
                ,qpid010BrokerMsgFtdDequeues
                ,qpid010BrokerByteFtdEnqueues
                ,qpid010BrokerByteFtdDequeues
                ,qpid010BrokerMsgFtdDepth
                ,qpid010BrokerByteFtdDepth
                ,qpid010BrokerReleases
                ,qpid010BrokerAcquires
                ,qpid010BrokerDiscardsNoRoute
                ,qpid010BrokerDiscardsTtl
                ,qpid010BrokerDiscardsRing
                ,qpid010BrokerDiscardsLvq
                ,qpid010BrokerDiscardsOverflow
                ,qpid010BrokerDiscardsSubscriber
                ,qpid010BrokerDiscardsPurge
                ,qpid010BrokerReroutes
                ,qpid010BrokerAbandoned
                ,qpid010BrokerAbandonedViaAlt
                ,qpid010AgentConnectionRef
                ,qpid010AgentLabel
                ,qpid010AgentRegisteredTo
                ,qpid010AgentSystemId
                ,qpid010AgentBrokerBank
                ,qpid010AgentAgentBank
                ,qpid010VhostBrokerRef
                ,qpid010VhostName
                ,qpid010VhostFederationTag
                ,qpid010QueueVhostRef
                ,qpid010QueueName
                ,qpid010QueueDurable
                ,qpid010QueueAutoDelete
                ,qpid010QueueExclusive
                ,qpid010QueueArguments
                ,qpid010QueueMsgTotalEnqueues
                ,qpid010QueueMsgTotalDequeues
                ,qpid010QueueMsgTxnEnqueues
                ,qpid010QueueMsgTxnDequeues
                ,qpid010QueueMsgPersistEnqueues
                ,qpid010QueueMsgPersistDequeues
                ,qpid010QueueMsgDepth
                ,qpid010QueueByteDepth
                ,qpid010QueueByteTotalEnqueues
                ,qpid010QueueByteTotalDequeues
                ,qpid010QueueByteTxnEnqueues
                ,qpid010QueueByteTxnDequeues
                ,qpid010QueueBytePersistEnqueues
                ,qpid010QueueBytePersistDequeues
                ,qpid010QueueMsgFtdEnqueues
                ,qpid010QueueMsgFtdDequeues
                ,qpid010QueueByteFtdEnqueues
                ,qpid010QueueByteFtdDequeues
                ,qpid010QueueMsgFtdDepth
                ,qpid010QueueByteFtdDepth
                ,qpid010QueueReleases
                ,qpid010QueueAcquires
                ,qpid010QueueDiscardsTtl
                ,qpid010QueueDiscardsRing
                ,qpid010QueueDiscardsLvq
                ,qpid010QueueDiscardsOverflow
                ,qpid010QueueDiscardsSubscriber
                ,qpid010QueueDiscardsPurge
                ,qpid010QueueReroutes
                ,qpid010QueueConsumerCount
                ,qpid010QueueConsumerCountLow
                ,qpid010QueueConsumerCountHi
                ,qpid010QueueBindingCount
                ,qpid010QueueBindingCountLow
                ,qpid010QueueBindingCountHi
                ,qpid010QueueUnackedMessages
                ,qpid010QueueUnackedMessagesLow
                ,qpid010QueueUnackedMessagesHi
                ,qpid010QueueMessageLatency
                ,qpid010QueueFlowStopped
                ,qpid010QueueFlowStoppedCount
                ,qpid010ExchangeVhostRef
                ,qpid010ExchangeName
                ,qpid010ExchangeType
                ,qpid010ExchangeDurable
                ,qpid010ExchangeAutoDelete
                ,qpid010ExchangeArguments
                ,qpid010ExchangeProducerCount
                ,qpid010ExchangeProducerCountLow
                ,qpid010ExchangeProducerCountHi
                ,qpid010ExchangeBindingCount
                ,qpid010ExchangeBindingCountLow
                ,qpid010ExchangeBindingCountHi
                ,qpid010ExchangeMsgReceives
                ,qpid010ExchangeMsgDrops
                ,qpid010ExchangeMsgRoutes
                ,qpid010ExchangeByteReceives
                ,qpid010ExchangeByteDrops
                ,qpid010ExchangeByteRoutes
                ,qpid010BindingExchangeRef
                ,qpid010BindingQueueRef
                ,qpid010BindingBindingKey
                ,qpid010BindingArguments
                ,qpid010BindingMsgMatched
                ,qpid010SubscriptionSessionRef
                ,qpid010SubscriptionQueueRef
                ,qpid010SubscriptionName
                ,qpid010SubscriptionBrowsing
                ,qpid010SubscriptionAcknowledged
                ,qpid010SubscriptionExclusive
                ,qpid010SubscriptionCreditMode
                ,qpid010SubscriptionArguments
                ,qpid010SubscriptionDelivered
                ,qpid010ConnectionVhostRef
                ,qpid010ConnectionAddress
                ,qpid010ConnectionIncoming
                ,qpid010ConnectionSystemConnection
                ,qpid010ConnectionUserProxyAuth
                ,qpid010ConnectionFederationLink
                ,qpid010ConnectionAuthIdentity
                ,qpid010ConnectionShadow
                ,qpid010ConnectionSaslMechanism
                ,qpid010ConnectionSaslSsf
                ,qpid010ConnectionClosing
                ,qpid010ConnectionFramesFromClient
                ,qpid010ConnectionFramesToClient
                ,qpid010ConnectionBytesFromClient
                ,qpid010ConnectionBytesToClient
                ,qpid010ConnectionMsgsFromClient
                ,qpid010ConnectionMsgsToClient
                ,qpid010LinkVhostRef
                ,qpid010LinkName
                ,qpid010LinkHost
                ,qpid010LinkPort
                ,qpid010LinkTransport
                ,qpid010LinkDurable
                ,qpid010LinkConnectionRef
                ,qpid010LinkState
                ,qpid010LinkLastError
                ,qpid010BridgeLinkRef
                ,qpid010BridgeName
                ,qpid010BridgeChannelId
                ,qpid010BridgeDurable
                ,qpid010BridgeSrc
                ,qpid010BridgeDest
                ,qpid010BridgeKey
                ,qpid010BridgeSrcIsQueue
                ,qpid010BridgeSrcIsLocal
                ,qpid010BridgeTag
                ,qpid010BridgeExcludes
                ,qpid010BridgeDynamic
                ,qpid010BridgeSync
                ,qpid010SessionVhostRef
                ,qpid010SessionName
                ,qpid010SessionChannelId
                ,qpid010SessionConnectionRef
                ,qpid010SessionDetachedLifespan
                ,qpid010SessionAttached
                ,qpid010SessionUnackedMessages
                ,qpid010SessionTxnStarts
                ,qpid010SessionTxnCommits
                ,qpid010SessionTxnRejects
                ,qpid010SessionTxnCount
                ,qpid010SessionClientCredit
                ,qpid010ManagementSetupStateObjectNum
                ,qpid010ManagementSetupStateBootSequence
                ,qpid010AclBrokerRef
                ,qpid010AclPolicyFile
                ,qpid010AclEnforcingAcl
                ,qpid010AclTransferAcl
                ,qpid010AclLastAclLoad
                ,qpid010AclMaxConnections
                ,qpid010AclMaxConnectionsPerIp
                ,qpid010AclMaxConnectionsPerUser
                ,qpid010AclAclDenyCount
                ,qpid010AclConnectionDenyCount
                ,qpid010ClusterBrokerRef
                ,qpid010ClusterClusterName
                ,qpid010ClusterClusterID
                ,qpid010ClusterMemberID
                ,qpid010ClusterPublishedURL
                ,qpid010ClusterClusterSize
                ,qpid010ClusterStatus
                ,qpid010ClusterMembers
                ,qpid010ClusterMemberIDs
                ,qpid010HaBrokerName
                ,qpid010HaBrokerStatus
                ,qpid010HaBrokerBrokersUrl
                ,qpid010HaBrokerPublicUrl
                ,qpid010HaBrokerReplicateDefault
                ,qpid010HaBrokerMembers
                ,qpid010HaBrokerSystemId
        }
        STATUS      current
        DESCRIPTION "Manditory class elements"
        ::= { qpid010CnfGroups 1 }

qpid010CnfGrpOptional OBJECT-GROUP
        OBJECTS {
                qpid010MemoryMallocarena
                ,qpid010MemoryMallocordblks
                ,qpid010MemoryMallochblks
                ,qpid010MemoryMallochblkhd
                ,qpid010MemoryMallocuordblks
                ,qpid010MemoryMallocfordblks
                ,qpid010MemoryMallockeepcost
                ,qpid010BrokerDataDir
                ,qpid010QueueAltExchange
                ,qpid010ExchangeAltExchange
                ,qpid010BindingOrigin
                ,qpid010ConnectionRemoteProcessName
                ,qpid010ConnectionRemotePid
                ,qpid010ConnectionRemoteParentPid
                ,qpid010SessionExpireTime
                ,qpid010SessionMaxClientRate
        }
        STATUS      current
        DESCRIPTION "Optional class elements"
        ::= { qpid010CnfGroups 2 }

qpid010CnfGrpArguments OBJECT-GROUP
        OBJECTS {
                qpid010EvtAltEx
                ,qpid010EvtArgs
                ,qpid010EvtAutoDel
                ,qpid010EvtDest
                ,qpid010EvtDisp
                ,qpid010EvtDurable
                ,qpid010EvtExName
                ,qpid010EvtExType
                ,qpid010EvtExcl
                ,qpid010EvtKey
                ,qpid010EvtQName
                ,qpid010EvtReason
                ,qpid010EvtRhost
                ,qpid010EvtUser
                ,qpid010EvtMsgDepth
                ,qpid010EvtByteDepth
                ,qpid010EvtAction
                ,qpid010EvtArguments
                ,qpid010EvtObjectName
                ,qpid010EvtObjectType
                ,qpid010EvtUserId
                ,qpid010EvtClientAddr
                ,qpid010EvtMembers
        }
        STATUS      current
        DESCRIPTION "Data objects used as arguments to events"
        ::= { qpid010CnfGroups 3 }


qpid010CnfGrpError NOTIFICATION-GROUP
        NOTIFICATIONS {
                qpid010EvtFileLoadFailed
        }
        STATUS      current
        DESCRIPTION "Events that are of severity Error"
        ::= { qpid010CnfGroups 4 }

qpid010CnfGrpInform NOTIFICATION-GROUP
        NOTIFICATIONS {
                qpid010EvtClientConnect
                ,qpid010EvtClientDisconnect
                ,qpid010EvtBrokerLinkUp
                ,qpid010EvtQueueDeclare
                ,qpid010EvtQueueDelete
                ,qpid010EvtExchangeDeclare
                ,qpid010EvtExchangeDelete
                ,qpid010EvtBind
                ,qpid010EvtUnbind
                ,qpid010EvtSubscribe
                ,qpid010EvtUnsubscribe
                ,qpid010EvtAllow
                ,qpid010EvtFileLoaded
                ,qpid010EvtMembersUpdate
        }
        STATUS      current
        DESCRIPTION "Events that are of severity Inform"
        ::= { qpid010CnfGroups 5 }

qpid010CnfGrpNotice NOTIFICATION-GROUP
        NOTIFICATIONS {
                qpid010EvtDeny
                ,qpid010EvtConnectionDeny
        }
        STATUS      current
        DESCRIPTION "Events that are of severity Notice"
        ::= { qpid010CnfGroups 6 }

qpid010CnfGrpWarn NOTIFICATION-GROUP
        NOTIFICATIONS {
                qpid010EvtClientConnectFail
                ,qpid010EvtBrokerLinkDown
                ,qpid010EvtQueueThresholdExceeded
        }
        STATUS      current
        DESCRIPTION "Events that are of severity Warn"
        ::= { qpid010CnfGroups 7 }


qpid010Compliance MODULE-COMPLIANCE
        STATUS      current
        DESCRIPTION "Manditory and non-manditory mib objects"
        MODULE -- This module
            MANDATORY-GROUPS { qpid010CnfGrpRequired,
                               qpid010CnfGrpOptional,
                               qpid010CnfGrpError,qpid010CnfGrpInform,qpid010CnfGrpNotice,qpid010CnfGrpWarn,
                               qpid010CnfGrpArguments }

        ::= { qpid010Conformance 2 }

END
